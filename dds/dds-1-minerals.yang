module dds-1-minerals {
  yang-version "1.1";
  namespace urn:test:dds-1-minerals;
  prefix dds-1;
  import minerals {
    prefix "m";
  } 
  organization
    "Test";
  contact
    "Test contact";
  description
    "DDS Option 1 Mineral Example";
  revision 2022-05-25 {
    description
      "Initial revision.";
    reference
      "dds option 1";
  }

  augment "/m:samples/m:sample" {
     description "Augment to add valid sample data";
     leaf streak-pattern {
        type string;
        config false;
        description "pattern of valid streak values";
     }
  }
}
