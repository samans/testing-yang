module mw-option {
  yang-version 1.1;
  namespace "urn:test:mw-option";
  prefix mwo;

  organization
    "Test";
  contact
    "Test contact";
  description
    "Option Backward Compatible Change Example";

  revision 2022-04-01 {
    description
      "Initial revision.";
    reference
      "mw-option test";
  }

  identity rlt-mode {
    description
      "Radio Link Terminal mode";
  }

  identity one-plus-zero {
    base rlt-mode;
  }

  identity one-plus-one {
    base rlt-mode;
  }

  identity two-plus-zero {
    base rlt-mode;
  }

  container rlt-db {
    description
      "Radio Link Terminal";
    leaf mode {
      type identityref {
        base rlt-mode;
      }
      mandatory true;
    }
  }
}
