module mw-option {
  yang-version 1.1;
  namespace "urn:test:mw-option";
  prefix mwo;

  organization
    "Test";
  contact
    "Test contact";
  description
    "Option Backward Compatible Change Example";

  revision 2022-05-26 {
    description
      "Change the way rlt mode is defined";
    reference
      "mw-option test";
  }
  revision 2022-04-01 {
    description
      "Initial revision.";
    reference
      "mw-option test";
  }

  identity rlt-mode {
    status deprecated;
    description
      "Radio Link Terminal mode";
  }

  identity one-plus-zero {
    base rlt-mode;
    status deprecated;
  }

  identity one-plus-one {
    base rlt-mode;
    status deprecated;
  }

  identity two-plus-zero {
    base rlt-mode;
    status deprecated;
  }

  container rlt-db {
    description
      "Radio Link Terminal";
    choice mode-option {
      mandatory true;
      leaf mode {
        status deprecated;
        type identityref {
          base rlt-mode;
        }
      }
      container rlt-mode {
        description
          "mode configuration";
        leaf num-bonded-carriers {
          type uint32;
          mandatory true;
          description
            "Number of bonded carriers";
        }
        leaf num-protecting-carriers {
          type uint32;
          mandatory true;
          description
            "Number of protecting carriers";
        }
      }
    }
  }
}
