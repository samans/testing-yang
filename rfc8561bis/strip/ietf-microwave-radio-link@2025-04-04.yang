module ietf-microwave-radio-link {
  yang-version 1.1;
  namespace "urn:ietf:params:xml:ns:yang:ietf-microwave-radio-link";
  prefix mrl;

  import ietf-yang-types {
    prefix yang;
    reference
      "RFC 6991";
  }
  import iana-if-type {
    prefix ianaift;
  }
  import ietf-interfaces {
    prefix if;
    reference
      "RFC 8343";
  }
  import ietf-interface-protection {
    prefix ifprot;
    reference
      "RFC 8561";
  }
  import ietf-microwave-types {
    prefix mw-types;
    reference
      "RFC 8561";
  }

  organization
    "Internet Engineering Task Force (IETF) CCAMP WG";
  contact
    "WG List: <mailto:ccamp@ietf.org>

     Editors:
      Jonas Ahlberg (jonas.ahlberg@ericsson.com)
      Min Ye (amy.yemin@huawei.com)
      Xi Li (Xi.Li@neclab.eu)
      Daniela Spreafico (daniela.spreafico@nokia.com)
      Marko Vaupotic (Marko.Vaupotic@aviatnet.com)
      Danilo Pala (danilo.pala@siaemic.com)";
  description
    "This is a module for the entities in
     a generic microwave system.

     Copyright (c) 2025 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX;
     see the RFC itself for full legal notices.";

  // RFC Ed.: replace XXXX with actual RFC number and remove
  // this note
  // replace the revision date with the module publication date
  // the format is (year-month-day)

  revision 2025-04-04 {
    description
      "Draft - Issue #32 Compression,
               Issue #35 grouping common-microwave-properties,
               Issue #31 added minimum-nominal-power";
    reference
      "RFC XXX: A YANG Data Model for Microwave Radio Link";
  }

  /*
   * Features
   */

  feature xpic {
    description
      "Indicates that the device supports XPIC.";
    reference
      "ETSI TR 102 311";
  }

  feature mimo {
    description
      "Indicates that the device supports MIMO.";
    reference
      "ETSI TR 102 311";
  }

  feature tdm {
    description
      "Indicates that the device supports TDM.";
  }

  feature header-compression {
    description
      "Indicates that the device supports Header Compression profiles.";
  }

  /*
   * Typedefs
   */

  grouping acm-profile {
    description
      "acm-profile";
    leaf modulation-scheme {
      type uint8;
      description
        "It is the logarithm base two of the number of points in the
         transmitted constellation.  E.G.:  value would be 2 for
         4QAM, 10 fo 1024QAM, and 12 for 4096QAM.";
    }
    leaf nominal-tx-capacity {
      type uint32;
      description
        "The nominal radio link capacity associated to this
         acm-profile.";
    }
    leaf support-as-fixed-modulation {
      type boolean;
      description
        "True when the profile can be used in single
         coding-modulation-mode.";
    }
    leaf support-as-reference-modulation {
      type boolean;
      description
        " 'true' when the profile can be used to configure the reference-modulation in adaptive
         coding-modulation-mode.
                 Otherwise the value is 'false' and the reference-modulation to use cannot be configured
                 (it could be selected automatically by the system).
                ";
    }
    leaf max-tx-power {
      type mw-types:power;
      description
        "The maximum transmitted power when the carrier termination
         is operating this acm-profile.  Used to configure
         transmitted power.";
    }
    leaf min-tx-power {
      type mw-types:power;
      description
        "The minimum transmitted power when the carrier termination
         is operating this acm-profile.  Used to configure
         transmitted power.";
    }
  }

  /*
   * Radio Link Terminal (RLT)
   */

  augment "/if:interfaces/if:interface" {
    when "derived-from-or-self(if:type,"
       + "'ianaift:microwaveRadioLinkTerminal')";
    description
      "Addition of data nodes for the radio link terminal to
       the standard Interface data model, for interfaces of
       the type 'microwaveRadioLinkTerminal'.";
    leaf id {
      type string;
      description
        "Descriptive identity of the radio link terminal used by
         far-end RLT to check that it's connected to the correct
         near-end RLT.  Does not need to be configured if this
         check is not used.";
    }
    choice mode-option {
      mandatory true;
      description
        "A description of the mode in which the radio link
         terminal is configured in terms of:
         - number of bonded carrier terminations;
         - number of protecting carrier terminations.";
      leaf mode {
        type identityref {
          base mw-types:rlt-mode;
        }
        mandatory true;
        status deprecated;
        description
          "A description of the mode in which the radio link
           terminal is configured.  The format is X plus Y.
           X represents the number of bonded carrier terminations.
           Y represents the number of protecting carrier
           terminations.

           This attribute has been deprecated: the rlt-mode container
           which provide flexible definitions of number of bonded
           carriers and protecting carriers should be used instead.";
      }
      container rlt-mode {
        description
          "This grouping provides a flexible definition of number
           of bonded carriers and protecting carriers of a radio
           link.";
        uses mw-types:rlt-mode;
      }
    }
    leaf-list carrier-terminations {
      type if:interface-ref;
      must "derived-from-or-self(/if:interfaces/if:interface"
         + "[if:name = current()]"
         + "/if:type, 'ianaift:microwaveCarrierTermination')" {
        description
          "The type of interface must be
           'microwaveCarrierTermination'.";
      }
      min-elements 1;
      description
        "A list of references to carrier terminations
         included in the radio link terminal.";
    }
    leaf-list rlp-groups {
      type leafref {
        path "/mrl:radio-link-protection-groups/"
           + "mrl:protection-group/mrl:name";
      }
      description
        "A list of references to the carrier termination
         groups configured for radio link protection in this
         radio link terminal.";
    }
    leaf-list xpic-pairs {
      if-feature "xpic";
      type leafref {
        path "/mrl:xpic-pairs/mrl:xpic-pair/mrl:name";
      }
      description
        "A list of references to the XPIC pairs used in this
         radio link terminal.  One pair can be used by two
         terminals.";
      reference
        "ETSI TR 102 311";
    }
    leaf-list mimo-groups {
      if-feature "mimo";
      type leafref {
        path "/mrl:mimo-groups/mrl:mimo-group/mrl:name";
      }
      description
        "A reference to the MIMO group used in this
         radio link terminal.  One group can be used by more
         than one terminal.";
      reference
        "ETSI TR 102 311";
    }
    list tdm-connections {
      if-feature "tdm";
      key "tdm-type";
      description
        "A list stating the number of active TDM connections
         of a specified tdm-type that is configured to be
         supported by the RLT.";
      leaf tdm-type {
        type identityref {
          base mw-types:tdm-type;
        }
        description
          "The type of TDM connection, which also indicates
           the supported capacity.";
      }
      leaf tdm-connections {
        type uint16;
        mandatory true;
        description
          "Number of connections of the specified type.";
      }
    }
    container header-compression {
      if-feature "header-compression";
      description
        "Configuration of Header Compression ";
      list supported-profile {
        key "name";
        config false;
        description
          "The list of header compression profiles supported by the RLT.

           Header compression is typically vendor proprietary and it is
           assumed there is no ambition to change that. For this reason
           the list provides only generic attributes to be augmented by
           vendor with proprietary implementation attributes.";
        leaf name {
          type string;
          description
            "A name that uniquely identifies the header compression profile
             in an RLT.";
        }
        leaf description {
          type string;
          description
            "Detailed description of the profile.";
        }
      }
      leaf configured-profile {
        type leafref {
          path "../mrl:supported-profile/mrl:name";
          require-instance false;
        }
        description
          "Select the profile of header compression to be used.";
      }
      leaf enabled {
        type boolean;
        description
          "Disables (false) or enables (true) the header compression.";
      }
      leaf oper-status {
        type enumeration {
          enum off {
            description
              "Header compression is off.";
          }
          enum on {
            description
              "Header compression is on.";
          }
        }
        config false;
        description
          "Shows the operative status of the header compression.";
      }
    }
  }

  /*
   * Carrier Termination
   */

  augment "/if:interfaces/if:interface" {
    when "derived-from-or-self(if:type,"
       + "'ianaift:microwaveCarrierTermination')";
    description
      "Addition of data nodes for carrier termination to
       the standard Interface data model, for interfaces
       of the type 'microwaveCarrierTermination'.";
    leaf carrier-id {
      type string;
      default "A";
      description
        "ID of the carrier (e.g., A, B, C, or D).
         Used in XPIC and MIMO configurations to check that
         the carrier termination is connected to the correct
         far-end carrier termination.  Should be the same
         carrier ID on both sides of the hop.  Left as
         default value when MIMO and XPIC are not in use.";
    }
    leaf tx-enabled {
      type boolean;
      default "false";
      description
        "Disables (false) or enables (true) the transmitter.
         Only applicable when the interface is enabled
         (interface:enabled = true); otherwise, it's always
         disabled.";
    }
    leaf tx-oper-status {
      type enumeration {
        enum off {
          description
            "Transmitter is off.";
        }
        enum on {
          description
            "Transmitter is on.";
        }
        enum standby {
          description
            "Transmitter is in standby.";
        }
      }
      config false;
      description
        "Shows the operative status of the transmitter.";
    }

    uses mw-types:common-microwave-properties;

    choice freq-or-distance {
      mandatory true;
      description
        "A choice to configure rx-frequency directly or compute
         it as duplex-distance subtracted from tx-frequency.";
      leaf rx-frequency {
        type uint32;
        units "kHz";
        description
          "Selected receiver frequency.";
      }
      leaf duplex-distance {
        type int32;
        units "kHz";
        description
          "Distance between transmitter and receiver frequencies.";
      }
    }
    leaf actual-duplex-distance {
      type uint32;
      units "kHz";
      config false;
      description
        "Computed distance between Tx and Rx frequencies.";
    }
    leaf polarization {
      type enumeration {
        enum horizontal {
          description
            "Horizontal polarization.";
        }
        enum vertical {
          description
            "Vertical polarization.";
        }
        enum not-specified {
          description
            "Polarization not specified.";
        }
      }
      default "not-specified";
      description
        "Polarization - a textual description for info only.";
    }
    choice power-mode {
      mandatory true;
      description
        "A choice of RTPC or ATPC.";
      container rtpc {
        description
          "Remote Transmit Power Control (RTPC).";
        reference
          "ETSI EN 302 217-1";
        leaf maximum-nominal-power {
          type mw-types:power {
            range "-99..99";
          }
          units "dBm";
          mandatory true;
          description
            "Selected output power.";
          reference
            "ETSI EN 302 217-1";
        }
      }
      container atpc {
        description
          "Automatic Transmitter Power Control (ATPC).";
        reference
          "ETSI EN 302 217-1";
        leaf maximum-nominal-power {
          type mw-types:power {
            range "-99..99";
          }
          units "dBm";
          mandatory true;
          description
            "Nominal maximum output power.";
          reference
            "ETSI EN 302 217-1";
        }
        leaf minimum-nominal-power {
          type mw-types:power {
            range "-99..99";
          }
          units "dBm";
          mandatory true;
          description
            "Minimum output power.

             By default, minimum output power is the same as the
             system capability minimum-power.";
        }
        leaf atpc-lower-threshold {
          type mw-types:power {
            range "-99..-20";
          }
          units "dBm";
          must 'current() <= ../atpc-upper-threshold';
          mandatory true;
          description
            "The lower threshold for the input power at the
             far end, which is used in the ATPC mode.";
          reference
            "ETSI EN 302 217-1";
        }
        leaf atpc-upper-threshold {
          type mw-types:power {
            range "-99..-20";
          }
          units "dBm";
          mandatory true;
          description
            "The upper threshold for the input power at the
             far end, which is used in the ATPC mode.";
          reference
            "ETSI EN 302 217-1";
        }
      }
    }
    leaf actual-received-level {
      type mw-types:power {
        range "-99..-20";
      }
      units "dBm";
      config false;
      description
        "Actual received power level (0.1 dBm resolution).";
      reference
        "ETSI EN 301 129";
    }
    choice coding-modulation-mode {
      mandatory true;
      description
        "A selection of single or
         adaptive coding/modulation mode.";
      container single {
        description
          "A single modulation order only.";
        reference
          "ETSI EN 302 217-1";
        leaf selected-cm {
          type identityref {
            base mw-types:coding-modulation;
          }
          mandatory true;
          description
            "Selected the single coding/modulation.";
        }
      }
      container adaptive {
        description
          "Adaptive coding/modulation.";
        reference
          "ETSI EN 302 217-1";
        leaf selected-min-acm {
          type identityref {
            base mw-types:coding-modulation;
          }
          mandatory true;
          description
            "Selected minimum coding/modulation.
             Adaptive coding/modulation shall not go
             below this value.";
        }
        leaf selected-max-acm {
          type identityref {
            base mw-types:coding-modulation;
          }
          mandatory true;
          description
            "Selected maximum coding/modulation.
             Adaptive coding/modulation shall not go
             above this value.";
        }
        leaf reference-modulation {
          type identityref {
            base mw-types:coding-modulation;
          }
          description
            "the reference-modulation is the coding modulation to be used in the reference mode, as defined in ETSI EN 302 217-1 V3.2.2 (2020-02).
                        The reference mode identifies the operative mode which characteristics (i.e. system capacity, spectral efficiency class over a given channel separation)
                        are used (i.e. declared in the licensing process) in the link per link coordination analysis.
                        Its value has to be between the 'selected-min-acm' and the 'selected-max-acm' attribute's values.
                        ";
        }
      }
    }
    leaf actual-xpi {
      if-feature "xpic";
      type decimal64 {
        fraction-digits 1;
        range "0..99";
      }
      units "dB";
      config false;
      description
        "The actual carrier to cross-polar interference.
         Only valid if XPIC is enabled (0.1 dB resolution).";
      reference
        "ETSI TR 102 311";
    }
    container ct-performance-thresholds {
      description
        "Specification of thresholds for when alarms should
         be sent and cleared for various performance counters.";
      leaf received-level-alarm-threshold {
        type mw-types:power {
          range "-99..-20";
        }
        units "dBm";
        default "-99";
        description
          "An alarm is sent when the received power level is
           below the specified threshold.";
        reference
          "ETSI EN 301 129";
      }
      leaf transmitted-level-alarm-threshold {
        type mw-types:power {
          range "-99..99";
        }
        units "dBm";
        default "-99";
        description
          "An alarm is sent when the transmitted power level
           is below the specified threshold.";
        reference
          "ETSI EN 301 129";
      }
      leaf ber-alarm-threshold {
        type enumeration {
          enum 1e-9 {
            description
              "Threshold at 1e-9 (10^-9).";
          }
          enum 1e-8 {
            description
              "Threshold at 1e-8 (10^-8).";
          }
          enum 1e-7 {
            description
              "Threshold at 1e-7 (10^-7).";
          }
          enum 1e-6 {
            description
              "Threshold at 1e-6 (10^-6).";
          }
          enum 1e-5 {
            description
              "Threshold at 1e-5 (10^-5).";
          }
          enum 1e-4 {
            description
              "Threshold at 1e-4 (10^-4).";
          }
          enum 1e-3 {
            description
              "Threshold at 1e-3 (10^-3).";
          }
          enum 1e-2 {
            description
              "Threshold at 1e-2 (10^-2).";
          }
          enum 1e-1 {
            description
              "Threshold at 1e-1 (10^-1).";
          }
        }
        default "1e-6";
        description
          "Specification of at which BER an alarm should
           be raised.";
        reference
          "ETSI EN 302 217-1";
      }
    }
    leaf if-loop {
      type enumeration {
        enum disabled {
          description
            "Disables the IF Loop.";
        }
        enum client {
          description
            "Loops the signal back to the client side.";
        }
        enum radio {
          description
            "Loops the signal back to the radio side.";
        }
      }
      default "disabled";
      description
        "Enable (client/radio) or disable (disabled)
         the IF Loop, which loops the signal back to
         the client side or the radio side.";
    }
    leaf rf-loop {
      type enumeration {
        enum disabled {
          description
            "Disables the RF Loop.";
        }
        enum client {
          description
            "Loops the signal back to the client side.";
        }
        enum radio {
          description
            "Loops the signal back to the radio side.";
        }
      }
      default "disabled";
      description
        "Enable (client/radio) or disable (disabled)
         the RF loop, which loops the signal back to
         the client side or the radio side.";
    }
    container capabilities {
      config false;
      description
        "Capabilities of the installed equipment and
         some selected configurations.";
      leaf min-tx-frequency {
        type uint32;
        units "kHz";
        description
          "Minimum Tx frequency possible to use.";
      }
      leaf max-tx-frequency {
        type uint32;
        units "kHz";
        description
          "Maximum Tx frequency possible to use.";
      }
      leaf min-rx-frequency {
        type uint32;
        units "kHz";
        description
          "Minimum Rx frequency possible to use.";
      }
      leaf max-rx-frequency {
        type uint32;
        units "kHz";
        description
          "Maximum Tx frequency possible to use.";
      }
      leaf minimum-power {
        type mw-types:power;
        units "dBm";
        description
          "The minimum output power supported.";
        reference
          "ETSI EN 302 217-1";
      }
      leaf maximum-available-power {
        type mw-types:power;
        units "dBm";
        description
          "The maximum output power supported.";
        reference
          "ETSI EN 302 217-1";
      }
      leaf available-min-acm {
        type identityref {
          base mw-types:coding-modulation;
        }
        description
          "Minimum coding-modulation possible to use.";
      }
      leaf available-max-acm {
        type identityref {
          base mw-types:coding-modulation;
        }
        description
          "Maximum coding-modulation possible to use.";
      }
      list acm-profile-list {
        key "profile-channel-separation-id "
          + "profile-coding-modulation-id";
        description
          "A list of acm-profile.
           Each acm-profile is identified by a channel-separation and
           coding-modulation values as supported by the carrier
           termination and defines the parameter's values of each
           transmission acm profile.
           Basically, the list contains all acm profiles supported by
           the device.  Profiles are organized into profile chains
           for each different channel separation value available. The
           chains are formed by the lower-acm-profile-ptr and
           upper-acm-profile-ptr pointers.  The sequence in the list
           reflects the sequence of profiles that are operated by the
           device according to the fading conditions, from the clear
           sky down to the persistent rain, and vice versa. The
           channel-separation and selected-cm configuration
           parameters (or the selected-min-acm/selected-max-acm
           pair) must address one of the profiles in the list.";
        leaf profile-channel-separation-id {
          type uint32;
          description
            "Uniquely identifies the acm profile (together with
             'profile-coding-modulation-id').  It could be used to
             allow the configuration of the channel-separation
             value.";
        }
        leaf profile-coding-modulation-id {
          type identityref {
            base mw-types:coding-modulation;
          }
          description
            "Uniquely identifies the acm profile (together with
             'profile-channel-separation-id').  It could be used to
             allow the configuration of the selected-cm (single
             mode) or selected-min-acm/selected-max-acm (adaptive
             mode).";
        }
        uses acm-profile;
        container lower-acm-profile-ptr {
          description
            "Together with the upper-acm-profile-ptr parameters it
             creates a chain of acm profiles related to a specific
             channel separation value.  Specifically it references
             the next lower acm-profile, while upper-acm-profile-ptr
             references the next higher profile.  The lowest profile
             in the chain, shall not instantiate this container.  The
             acm-profile-list can contain multiple chains related to
             different channel separation values supported by the
             device.";
          leaf profile-coding-modulation-id-ref {
            type leafref {
              path "../../../acm-profile-list"
                 + "/profile-coding-modulation-id";
            }
            description
              "A reference to an acm-profile to give an order in
               acm-profile-list.  This is the reference to the
               'profile-coding-modulation-id' key of the next lower
               acm-profile in the list respect to the current one.";
          }
          leaf profile-channel-separation-id-ref {
            type leafref {
              path "../../.."
                 + "/acm-profile-list[profile-coding-modulation-id="
                 + "current()/../profile-coding-modulation-id-ref]"
                 + "/profile-channel-separation-id";
            }
            description
              "A reference to an acm-profile to give an order in
               acm-profile-list.  This is the reference to the
               'profile-channel-separation-id' key of the next lower
               acm-profile in the list respect to the current one.";
          }
        }
        container upper-acm-profile-ptr {
          description
            "Together with the lower-acm-profile-ptr parameters it
             creates a chain of acm profiles related to a specific
             channel separation value.  Specifically it references
             the next higher acm-profile, while lower-acm-profile-ptr
             references the next lower profile.  The highest profile
             in the chain, shall not instantiate this container.  The
             acm-profile-list can contain multiple chains related to
             different channel separation values supported by the
             device.";
          leaf profile-coding-modulation-id-ref {
            type leafref {
              path "../../../acm-profile-list"
                 + "/profile-coding-modulation-id";
            }
            description
              "A reference to an acm-profile to give an order in
               acm-profile-list.  This is the reference to the
               'profile-coding-modulation-id' key of the next higher
               acm-profile in the list respect to the current one.";
          }
          leaf profile-channel-separation-id-ref {
            type leafref {
              path "../../.."
                 + "/acm-profile-list[profile-coding-modulation-id="
                 + "current()/../profile-coding-modulation-id-ref]"
                 + "/profile-channel-separation-id";
            }
            description
              "A reference to an acm-profile to give an order in
               acm-profile-list.  This is the reference to the
               'profile-channel-separation-id' key of the next higher
               acm-profile in the list respect to the current one.";
          }
        }
      }
    }
    container error-performance-statistics {
      config false;
      description
        "ITU-T G.826 error performance statistics relevant for
         a microwave/millimeter wave carrier.";
      leaf bbe {
        type yang:counter32;
        units "number of block errors";
        description
          "Number of Background Block Errors (BBEs).  A BBE is an
           errored block not occurring as part of Severely Errored
           Seconds (SES).  Discontinuities in the value of this
           counter can occur at re-initialization of the management
           system and at other times as indicated by the value of
           'discontinuity-time' in ietf-interfaces.";
        reference
          "ITU-T G.826";
      }
      leaf es {
        type yang:counter32;
        units "seconds";
        description
          "Number of Errored Seconds (ES).  An ES is a one-second
           period with one or more errored blocks or at least one
           defect.  Discontinuities in the value of this counter
           can occur at re-initialization of the management system
           and at other times as indicated by the value of
           'discontinuity-time' in ietf-interfaces.";
        reference
          "ITU-T G.826";
      }
      leaf ses {
        type yang:counter32;
        units "seconds";
        description
          "Number of SES.  SES is a one-second period that contains
           equal or more than 30% errored blocks or at least
           one defect.  SES is a subset of ES.  Discontinuities in
           the value of this counter can occur at re-initialization
           of the management system and at other times as indicated
           by the value of 'discontinuity-time' in ietf-interfaces.";
        reference
          "ITU-T G.826";
      }
      leaf uas {
        type yang:counter32;
        units "seconds";
        description
          "Number of Unavailable Seconds (UAS); that is, the
           total time that the node has been unavailable.
           Discontinuities in the value of this counter can occur
           at re-initialization of the management system and at
           other times as indicated by the value of
           'discontinuity-time' in ietf-interfaces.";
        reference
          "ITU-T G.826";
      }
    }
    container radio-performance-statistics {
      config false;
      description
        "ETSI EN 301 129 radio physical interface statistics relevant
         for a carrier termination.";
      leaf min-rltm {
        type mw-types:power {
          range "-99..-20";
        }
        units "dBm";
        description
          "Minimum received power level.  Discontinuities in the
           value of this counter can occur at re-initialization
           of the management system and at other times as
           indicated by the value of 'discontinuity-time' in
           ietf-interfaces.";
        reference
          "ETSI EN 301 129";
      }
      leaf max-rltm {
        type mw-types:power {
          range "-99..-20";
        }
        units "dBm";
        description
          "Maximum received power level.  Discontinuities in the
           value of this counter can occur at re-initialization
           of the management system and at other times as
           indicated by the value of 'discontinuity-time' in
           ietf-interfaces.";
        reference
          "ETSI EN 301 129";
      }
      leaf min-tltm {
        type mw-types:power {
          range "-99..99";
        }
        units "dBm";
        description
          "Minimum transmitted power level.  Discontinuities
           in the value of this counter can occur at
           re-initialization of the management system and
           at other times as indicated by the value of
           'discontinuity-time' in ietf-interfaces.";
        reference
          "ETSI EN 301 129";
      }
      leaf max-tltm {
        type mw-types:power {
          range "-99..99";
        }
        units "dBm";
        description
          "Maximum transmitted power level.  Discontinuities
           in the value of this counter can occur at
           re-initialization of the management system and
           at other times as indicated by the value of
           'discontinuity-time' in ietf-interfaces.";
        reference
          "ETSI EN 301 129";
      }
    }
  }

  /*
   * Radio Link Protection Groups
   */

  container radio-link-protection-groups {
    description
      "Configuration of radio link protected groups of
       carrier terminations in a radio link.  More than one
       protected group per radio link terminal is allowed.";
    uses ifprot:protection-groups {
      refine "protection-group/members" {
        must "derived-from-or-self(/if:interfaces/if:interface"
           + "[if:name = current()]"
           + "/if:type, 'ianaift:microwaveCarrierTermination')" {
          description
            "The type of a protection member must be
             'microwaveCarrierTermination'.";
        }
      }
      refine "protection-group/working-entity" {
        must "derived-from-or-self(/if:interfaces/if:interface"
           + "[if:name = current()]"
           + "/if:type, 'ianaift:microwaveCarrierTermination')" {
          description
            "The type of a working-entity must be
             'microwaveCarrierTermination'.";
        }
      }
    }
  }

  /*
   * XPIC & MIMO groups - Configuration data nodes
   */

  container xpic-pairs {
    if-feature "xpic";
    description
      "Configuration of carrier termination pairs
       for operation in XPIC mode.";
    reference
      "ETSI TR 102 311";
    list xpic-pair {
      key "name";
      description
        "List of carrier termination pairs in XPIC mode.";
      leaf name {
        type string;
        description
          "Name used for identification of the XPIC pair.";
      }
      leaf enabled {
        type boolean;
        default "false";
        description
          "Enable(true)/disable(false) XPIC";
      }
      leaf-list members {
        type if:interface-ref;
        must "derived-from-or-self(/if:interfaces/if:interface"
           + "[if:name = current()]"
           + "/if:type, 'ianaift:microwaveCarrierTermination')" {
          description
            "The type of a member must be
             'microwaveCarrierTermination'.";
        }
        min-elements 2;
        max-elements 2;
        description
          "Association to XPIC pairs used in the radio link
           terminal.";
      }
    }
  }
  container mimo-groups {
    if-feature "mimo";
    description
      "Configuration of carrier terminations
       for operation in MIMO mode.";
    reference
      "ETSI TR 102 311";
    list mimo-group {
      key "name";
      description
        "List of carrier terminations in MIMO mode.";
      leaf name {
        type string;
        description
          "Name used for identification of the MIMO group.";
      }
      leaf enabled {
        type boolean;
        default "false";
        description
          "Enable(true)/disable(false) MIMO.";
      }
      leaf-list members {
        type if:interface-ref;
        must "derived-from-or-self(/if:interfaces/if:interface"
           + "[if:name = current()]"
           + "/if:type, 'ianaift:microwaveCarrierTermination')" {
          description
            "The type of a member must be
             'microwaveCarrierTermination'.";
        }
        min-elements 2;
        description
          "Association to a MIMO group if used in the radio
           link terminal.";
      }
    }
  }
}
