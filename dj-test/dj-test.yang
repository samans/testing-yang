module dj-test {
  yang-version 1.1;
  namespace "urn:test:dj-test";
  prefix djt;

  organization
    "Test";
  contact
    "Test contact";
  description
    "Qdj test options";

  revision 2022-06-30 {
    description
      "NACM options test";
    reference
      "dj test";
  }

  container tsn-uni {
    description
      "TSN UNI";

    list domain {
        key "domain-id";

        leaf domain-id {
           type string;
        }

        list cuc {
           key "cuc-id";

           leaf cuc-id {
              type string;
           }
           list stream {
               key "stream-id";

               leaf stream-id {
                  type string;
               }
           }
        }
    } 
  }
}
