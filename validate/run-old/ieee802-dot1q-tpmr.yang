module ieee802-dot1q-tpmr {
  namespace urn:ieee:std:802.1Q:yang:ieee802-dot1q-tpmr;
  prefix dot1q-tpmr;
  import ieee802-dot1q-bridge {
    prefix dot1q;
  }
  import ietf-yang-types {
    prefix yang;
  }
  import ietf-interfaces {
    prefix if;
  }
  organization
    "IEEE 802.1 Working Group";
  contact
    "WG-URL: http://ieee802.org/1/
    WG-EMail: stds-802-1-l@ieee.org
    
    Contact: IEEE 802.1 Working Group Chair
    Postal: C/O IEEE 802.1 Working Group
            IEEE Standards Association
            445 Hoes Lane
            Piscataway, NJ 08854
            USA
    
    E-mail: stds-802-1-chairs@ieee.org";
  description
    "This YANG module describes the bridge configuration model for the
    Two Port MAC Relays. 

    Copyright (C) IEEE (2021). 

    This version of this YANG module is part of IEEE Std 802.1Q; see the standard itself for
    full legal notices.";
  revision 2021-06-01 {
    description
      "Published as part of IEEE Std 802.1Q-2021. Third version.";
    reference
      "IEEE Std 802.1Q-2021, Bridges and Bridged Networks.";
  }
  revision 2020-06-04 {
    description
      "Published as part of IEEE Std 802.1Qcx-2020. Second version.";
    reference
      "IEEE Std 802.1Qcx-2020, Bridges and Bridged Networks - YANG Data
      Model for Connectivity Fault Management.";
  }
  revision 2018-09-30 {
    description
      "Creation for Working Group review.";
    reference
      "IEEE Std 802.1Q-2018, Bridges and Bridged Networks.";
  }
  revision 2018-03-07 {
    description
      "Published as part of IEEE Std 802.1Q-2018. Initial version.";
    reference
      "IEEE Std 802.1Q-2018, Bridges and Bridged Networks.";
  }
  augment "/if:interfaces/if:interface/dot1q:bridge-port" {
    when
      "dot1q:port-type = 'dot1q:d-bridge-port'" {
      description
        "Applies to TPMRs ports";
    }
    description
      "Augment Interface model with TPMR port configuration specific
      nodes.";
    leaf managed-address {
      type boolean;
      default "true";
      description
        "A Boolean value, which is TRUE if the MAC address is the
        management address for the TPMR, and is otherwise FALSE.
        
        The TPMR management entity may make use of one or both Ports of a
        TPMR to transmit and receive management frames. However, the MAC
        address used by the TPMR management entity as the source MAC
        address in transmitted management frames (the management MAC
        address) is the individual MAC address associated with one of the
        Ports of the TPMR";
      reference
        "12.19.1.1.1.3 of IEEE Std 802.1Q-2021";
    }
    container mac-status-propagation {
      description
        "MAC status propagation configuration node parameters.";
      leaf link-notify {
        type boolean;
        default "true";
        description
          "The current value (Boolean) of LinkNotify (23.5.1) being used
          by the MSP state machines.";
        reference
          "12.19.4.1.1.3, 12.19.4.1.2.2 of IEEE Std 802.1Q-2021";
      }
      leaf link-notify-wait {
        type yang:timeticks {
          range "20..100";
        }
        default "40";
        description
          "The current value, in centiseconds, of LinkNotifyWait (23.5.2)
          being used by the MSP state machines.";
        reference
          "12.19.4.1.1.3, 12.19.4.1.2.2 of IEEE Std 802.1Q-2021";
      }
      leaf link-notify-retry {
        type yang:timeticks {
          range "10..100";
        }
        default "100";
        description
          "The current value, in centiseconds, of LinkNotifyRetry
          (23.5.3) being used by the MSP state machines.";
        reference
          "12.19.4.1.1.3, 12.19.4.1.2.2 of IEEE Std 802.1Q-2021";
      }
      leaf mac-notify {
        type boolean;
        default "true";
        description
          "The current value (Boolean) of MACNotify (23.5.4) being used
          by the MSP state machines.";
        reference
          "12.19.4.1.1.3, 12.19.4.1.2.2 of IEEE Std 802.1Q-2021";
      }
      leaf mac-notify-time {
        type yang:timeticks {
          range "1..50";
        }
        default "20";
        description
          "The current value, in centiseconds, of MACNotifyTime (23.5.5)
          being used by the MSP state machines.";
        reference
          "12.19.4.1.1.3, 12.19.4.1.2.2 of IEEE Std 802.1Q-2021";
      }
      leaf mac-recover-time {
        type yang:timeticks {
          range "2..50";
        }
        default "10";
        description
          "The current value, in centiseconds, of MACRecoverTime (23.5.6)
          being used by the MSP state machines.";
        reference
          "12.19.4.1.1.3, 12.19.4.1.2.2 of IEEE Std 802.1Q-2021";
      }
    }
  }
  augment
    "/if:interfaces/if:interface/dot1q:bridge-port/dot1q:statistics" {
    when
      "../dot1q:port-type = 'dot1q:d-bridge-port'" {
      description
        "Applies to TPMRs ports";
    }
    description
      "Augment Interface model with TPMR port operational state specific
      nodes.";
    leaf acks-tx {
      type yang:counter64;
      config false;
      description
        "The number of acks transmitted (23.6.15) by the Ports Transmit
        Process as a consequence of txAck being set.
        
        Discontinuities in the value of this counter can occur at
        re-initialization of the management system, and at other times as
        indicated by the value of 'discontinuity-time'.";
      reference
        "12.19.4.1.3.3 of IEEE Std 802.1Q-2021";
    }
    leaf add-notificatons-tx {
      type yang:counter64;
      config false;
      description
        "The number of adds transmitted (23.6.16) by the Ports Transmit
        Process as a consequence of txAdd being set.
        
        Discontinuities in the value of this counter can occur at
        re-initialization of the management system, and at other times as
        indicated by the value of 'discontinuity-time'.";
      reference
        "12.19.4.1.3.3 of IEEE Std 802.1Q-2021";
    }
    leaf add-confirmations-tx {
      type yang:counter64;
      config false;
      description
        "The number of add confirms transmitted (23.6.17) by the Ports
        Transmit Process as a consequence of txAddConfirm being set.
        
        Discontinuities in the value of this counter can occur at
        re-initialization of the management system, and at other times as
        indicated by the value of 'discontinuity-time'.";
      reference
        "12.19.4.1.3.3 of IEEE Std 802.1Q-2021";
    }
    leaf loss-notification-tx {
      type yang:counter64;
      config false;
      description
        "The number of losses transmitted (23.6.18) by the Ports Transmit
        Process as a consequence of txLoss being set.
        
        Discontinuities in the value of this counter can occur at
        re-initialization of the management system, and at other times as
        indicated by the value of 'discontinuity-time'.";
      reference
        "12.19.4.1.3.3 of IEEE Std 802.1Q-2021";
    }
    leaf loss-confirmation-tx {
      type yang:counter64;
      config false;
      description
        "The number of loss confirms transmitted (23.6.19) by the Ports
        Transmit Process as a consequence of txLossConfirm being set.
        
        Discontinuities in the value of this counter can occur at
        re-initialization of the management system, and at other times as
        indicated by the value of 'discontinuity-time'.";
      reference
        "12.19.4.1.3.3 of IEEE Std 802.1Q-2021";
    }
    leaf acks-rx {
      type yang:counter64;
      config false;
      description
        "The number of acks received (23.6.10) by the Ports Transmit
        Process.
        
        Discontinuities in the value of this counter can occur at
        re-initialization of the management system, and at other times as
        indicated by the value of 'discontinuity-time'.";
      reference
        "12.19.4.1.3.3 of IEEE Std 802.1Q-2021";
    }
    leaf add-notificatons-rx {
      type yang:counter64;
      config false;
      description
        "The number of adds received (23.6.11) by the Ports Receive
        Process.
        
        Discontinuities in the value of this counter can occur at
        re-initialization of the management system, and at other times as
        indicated by the value of 'discontinuity-time'.";
      reference
        "12.19.4.1.3.3 of IEEE Std 802.1Q-2021";
    }
    leaf add-confirmations-rx {
      type yang:counter64;
      config false;
      description
        "The number of add confirms received (23.6.12) by the Ports
        Receive Process.
        
        Discontinuities in the value of this counter can occur at
        re-initialization of the management system, and at other times as
        indicated by the value of 'discontinuity-time'.";
      reference
        "12.19.4.1.3.3 of IEEE Std 802.1Q-2021";
    }
    leaf loss-notification-rx {
      type yang:counter64;
      config false;
      description
        "The number of losses received (23.6.13) by the Ports Receive
        Process.
        
        Discontinuities in the value of this counter can occur at
        re-initialization of the management system, and at other times as
        indicated by the value of 'discontinuity-time'.";
      reference
        "12.19.4.1.3.3 of IEEE Std 802.1Q-2021";
    }
    leaf loss-confirmation-rx {
      type yang:counter64;
      config false;
      description
        "The number of loss confirms received (23.6.14) by the Ports
        Receive Process.
        
        Discontinuities in the value of this counter can occur at
        re-initialization of the management system, and at other times as
        indicated by the value of 'discontinuity-time'.";
      reference
        "12.19.4.1.3.3 of IEEE Std 802.1Q-2021";
    }
    leaf add-events {
      type yang:counter64;
      config false;
      description
        "The number of transitions to STM:ADD directly from STM:DOWN or
        STM:LOSS (23.8).
        
        Discontinuities in the value of this counter can occur at
        re-initialization of the management system, and at other times as
        indicated by the value of 'discontinuity-time'.";
      reference
        "12.19.4.1.3.3 of IEEE Std 802.1Q-2021";
    }
    leaf loss-events {
      type yang:counter64;
      config false;
      description
        "The number of transitions to STM:LOSS directly from STM:UP or
        STM:ADD (23.8).
        
        Discontinuities in the value of this counter can occur at
        re-initialization of the management system, and at other times as
        indicated by the value of 'discontinuity-time'.";
      reference
        "12.19.4.1.3.3 of IEEE Std 802.1Q-2021";
    }
    leaf mac-status-notifications {
      type yang:counter64;
      config false;
      description
        "The number of transitions to SNM:MAC_NOTIFICATION (23.9).
        
        Discontinuities in the value of this counter can occur at
        re-initialization of the management system, and at other times as
        indicated by the value of 'discontinuity-time'.";
      reference
        "12.19.4.1.3.3 of IEEE Std 802.1Q-2021";
    }
  }
}
