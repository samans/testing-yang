module ieee802-dot1ae-pry {
  yang-version "1.1";
  namespace urn:ieee:std:802.1AE:yang:ieee802-dot1ae-pry;
  prefix dot1ae-pry;
  import ietf-interfaces {
    prefix if;
  }
  import ietf-yang-types {
    prefix yang;
  }
  import ieee802-dot1q-types {
    prefix dot1q-types;
  }
  import ieee802-types {
    prefix ieee;
  }
    import iana-if-type {
    prefix ianaift;
  }

  organization
   "IEEE 802.1 Working Group";
  contact
    "WG-URL: http:ieee802.org/1/
    WG-EMail: stds-802-1-l@ieee.org
    
    Contact: IEEE 802.1 Working Group Chair
    Postal: C/O IEEE 802.1 Working Group
           IEEE Standards Association
           445 Hoes Lane
           Piscataway, NJ 08855
           USA
    
    E-mail: stds-802-1-chairs@ieee.org";
  description
    "This YANG module augments the configuration and operational state
    data for interfaces for the MAC Privacy project. IEEE 802.1AEdk";
  revision 2021-06-21 {
    description
      "Initial revision.";
  }
  
  /*--------------------*/
  /* Feature            */
  /*--------------------*/
  feature macsec-priv {
    description
      "Feature MAC Privacy";
  }
  
  /*--------------------*/
  /*   identities       */
  /*--------------------*/
  identity priority-map-identity {
    description
      "Base identity for assigning a priority to a Privacy type";
  }
  identity channel-identity {
    description
      "Base identity for privacy channel";
  }
  identity express-channel {
    base channel-identity;
    base priority-map-identity;
    description
      "This is the express privacy channel frame designation.";
    reference
      "20.13.4 of IEEE 802.1AEdk";
  }
  identity preemptable-channel {
    base channel-identity;
    base priority-map-identity;
    description
      "This is the preemptable privacy channel designation.";
    reference
      "20.13.4 of IEEE 802.1AEdk";
  }
  identity frame-identity {
    description
      "Base identity for privacy frame";
  }
  identity frame {
    base frame-identity;
    base priority-map-identity;
    description
      "This is a privacy frame. A frame-a must be designated for this
      frame if frame-a mapping is used.";   
    reference 
      "20.13.5.1 of IEEE 802.1AEdk";
  }
  identity none-identity {
    description
      "Base identity for privacy frame";
  }
  identity none {
    base none-identity;
    base priority-map-identity;
    description
      "This is no privacy encapsulation. Frames mapped to this identity
       are forwarded directly without MAC privacy encapsulation.";
    reference
      "20.13.5.1 of IEEE 802.1AEdk";
  }
  identity fragment-ordering-identity {
    description
      "Base identity for privacy frame ordering";
  }
  identity default-strict-ordered {
    base fragment-ordering-identity;
    description
      "This is the default supported by the standard - process
       fragments in strict order. In many cases ordering 
       is ensured by MACsec. If vendors desired to support
       handling of occasional MPPDU reordering this 
       identity can be augmented to allow setting. 
       This is a receive only parameter.";
    reference
      "20.13.5.1 of IEEE 802.1AEdk";
  }
  
  /*--------------------*/
  /* Configuration Data */
  /*--------------------*/
  augment "/if:interfaces/if:interface" {
    if-feature "macsec-priv";
    description
      "MACsec Privacy Mode";
    when
      "if:type = 'ianaift:ethernetCsmacd' or if:type = "+
      "'ianaift:ilan' or if:type = 'ianaift:macSecControlledIF' or "+
      "if:type = 'ianaift:ptm' or if:type = 'ianaift:bridge'" {
      description
        "Augment interfaces with 802.1ae MACSec System specific
        configuration nodes.";
    }
    container pry {
      description
        "Configure the MAC Privacy Options";
      container reception {
        description
          "Configure the MAC Privacy Reception";
        leaf max-peers {
          type uint8;
          description 
            "Max supported Group Address peers. This is vendor 
             dependent on the number of simultaneous channels 
             supporting fragmentation. Note that fragment 
             ordering and non fragmenting sources has an
             an impact on this number.";
        }
        leaf-list peer-src-address {
          type ieee:mac-address;
          description
            "List of Valid group address Peers. This list
             cannot be greater than the max supported.";
        }                   
        leaf fragment-ordering {
          type identityref {
              base fragment-ordering-identity;
          }
          default default-strict-ordered;
          description
            "An identity that determines whether misordered 
             fragments can be assembled. The standard supports 
             strict ordered but this can augmented by vendors 
             to allows misordered frames";
          reference
            "20.13.5.1 of IEEE 802.1AEdk";
        }
      }
      container reception-stats {
        description
          "Configure the MAC Privacy Reception Statistics";
        leaf in-user-protected-frames {
          type yang:counter64;
          config false;
          description
            "Total number of MAC Privacy user frames received.";
          reference
            "20.13.8 of IEEE 802.1AEdk";
        }
        leaf in-user-protected-octets {
          type yang:counter64;
          config false;
          description
            "Total number of MAC Privacy user frames received.";
          reference
            "20.13.8 of IEEE 802.1AEdk";
        }
        leaf in-mppdus {
          type yang:counter64;
          config false;
          description
            "Total number of MAC Privacy PDUs received.";
          reference
            "20.13.8 of IEEE 802.1AEdk";
        }
        leaf in-encapsulated-frames {
          type yang:counter64;
          config false;
          description
            "Total number of MAC Privacy user frames received
             that were not fragmented.";
          reference
            "20.13.8 of IEEE 802.1AEdk";
        }
        leaf in-user-express-fragments {
          type yang:counter64;
          config false;
          description
            "Total number of MAC Privacy user express frames received.";
          reference
            "20.13.8 of IEEE 802.1AEdk";
        }
        leaf in-user-preemptable-fragments {
          type yang:counter64;
          config false;
          description
            "Total number of MAC Privacy user preemptable frames received.";
          reference
            "20.13.8 of IEEE 802.1AEdk";
        }
        leaf in-express-discard-fragments {
          type yang:counter64;
          config false;
          description
            "Total number of MAC Privacy user express fragments 
	     discarded.";
          reference
            "20.13.8 of IEEE 802.1AEdk";
        }
        leaf in-preemptable-discard-fragments {
          type yang:counter64;
          config false;
          description
            "Total number of MAC Privacy user preemptable fragments 
	     discarded.";
          reference
            "20.13.8 of IEEE 802.1AEdk";
        }
        leaf in-pad-octets {
          type yang:counter64;
          config false;
          description
            "Total number of MAC Privacy pad octets received.";
          reference
            "20.13.8 of IEEE 802.1AEdk";
        }
        leaf in-unknown-mppcis {
          type yang:counter64;
          config false;
          description
            "Total number of MAC Privacy Components not recognized
            and dropped.";
          reference
            "20.13.8 of IEEE 802.1AEdk";
        }
        leaf in-errored-mppdus {
          type yang:counter64;
          config false;
          description
            "Total number of MAC Privacy PDUs dropped due to errors.";
          reference
            "20.13.8 of IEEE 802.1AEdk";
        }
        leaf in-user-express-frames {
          type yang:counter64;
          config false;
          description
            "Total number of MAC Privacy user express frames received.";
          reference
            "20.13.8 of IEEE 802.1AEdk";
        }
        leaf in-user-preemptable-frames {
          type yang:counter64;
          config false;
          description
            "Total number of MAC Privacy user preemptable frames received.";
          reference
            "20.13.8 of IEEE 802.1AEdk";
        }
        leaf in-user-unprotected-frames {
          type yang:counter64;
          config false;
          description
            "Total number of frames with no privacy protection received.";
          reference
            "20.13.8 of IEEE 802.1AEdk";
        }
        leaf in-user-unprotected-octets {
          type yang:counter64;
          config false;
          description
            "Total number of octets with no privacy protection received.";
          reference
            "20.13.8 of IEEE 802.1AEdk";
        }
      }
      container transmission {
        description
          "Configure the MAC Privacy Transmission";
        leaf privacy-protection {
          type boolean; 
          default true;
          description
            "MACSec Privacy Enable - True or False.";
          reference
            "20.13.1 of IEEE 802.1AEdk";
        }
        leaf pry-source-address {
          type ieee:mac-address;
          config false;
          description
            "The individual MAC address of the MAC Privacy service. 
            This address is read only and determined by the system.  
            Normally it is shared with PAE";
          reference
            "20.13.2 of IEEE 802.1AEdk)";
        }
        leaf use-mka-group-address {
          type boolean;
          default true; 
          description
            "When set to true the MPPDU destination address used by this 
            PRY is shared with the PAE. When set to false a configured
            destination may override the system MAC address.";
          reference
            "20.13.6.7 of IEEE 802.1AEdk";
        }
        leaf mppdu-dest-address {
          when "../dot1ae-pry:use-mka-group-address='false'";
          type ieee:mac-address;
          description
            "The individual or group MAC address of the MAC Privacy
            service. This MAC identifies one or more destinations
            and is normally the address shared with PAE. It may 
            be configured to another address when use-pae-dest-address 
            is set to false";
          reference
            "20.13.3 of IEEE 802.1AEdk";
        }
        leaf fragment-enable {
          type boolean;
          config true;
          default true; 
          description
            "Fragmentation control for this channel. It is recommended 
             to use fragmentation at all times for efficiency and minimizing 
             delay. This control allows for showing the effects of fragmentation
             vs no fragmentation or simple performance tests.";
          reference
            "20.13.6.7 of IEEE 802.1AEdk";
        }
        list user-priority-to-pry {
          key "user-priority";
          description
            "User priority is mapped to privacy channels express or preemptable
            or to privacy frames";
          reference
            "";
          leaf user-priority {
            type uint8 {
              range "0..7";
            }
            description
              "There are eight values of User Priority that map to ether a
              priority channel or a priority frame.";
            reference
              "20.13.5.1 of IEEE 802.1AEdk";
          }
          leaf privacy-type {
            type identityref {
              base priority-map-identity;
            }
            mandatory true;
            description
              "An identity associated with the privacy channel or frame.";
            reference
              "20.13.5.1 of IEEE 802.1AEdk";
          }
          leaf frame-access-priority {
            when "../dot1ae-pry:privacy-type='dot1ae-pry:frame'";
            type dot1q-types:priority-type;
            description
              "Access Priority of the frames that are mapped to 
               the Frame table";
            reference
                "20.13.6.2, 20.13.7.2 of IEEE 802.1AEdk";
          }
          leaf frame-reveal-de {
            when "../dot1ae-pry:privacy-type='dot1ae-pry:frame'";
            type enumeration {
              enum hidden {
                value 0;
              }
              enum visible {
                value 1;
              }
            }
            default hidden;
            description
              "For privacy frames only, this parameter allows Privacy frames 
               with transmit discard eligible set to be visible and
               set on the encapsulated frame. ";
            reference
                "20.13.6.2, 20.13.7.2 of IEEE 802.1AEdk";
          }
          leaf frame-privacy-padding {
            when "../dot1ae-pry:privacy-type='dot1ae-pry:frame'";
            type enumeration { 
              enum none {
                value 0;
              }
              enum to-16 {
                value 1;
              }
              enum to-32 {
                value 2;
              }
              enum to-64 {
                value 3;
              }
            }
            default to-64;
            description
              "The privacy padding to a nearest multiple. None is an 
              unpadded frame or variable length.   Padding is
              add up to a boundary. In the case of Ethernet 
              interfaces it also excludes the 4-8 byte overhead
              of any known (i.e. explicitly matched by a child
              sub-interface) 802.1Q VLAN tags."; 
            reference
              "20.13.7.3 of IEEE 802.1AEdk";
          }
        }
        container frame {
          presence "Common Frame parameters";
          description
            "Frame attributes";
          reference
            "20.13.6.6 of IEEE 802.1AEdk";
          leaf user-data-frame-size {
            type uint16 {
              range "128 .. 9100";
            }
            units octets;
            default 1518;
            description
              "The maximum size in octets of layer 2 frames that may be
              transmitted or received on the interface (excluding any FCS
              overhead). This size is what you would expect to be capable to 
              carry a single l2 maximum user size frame unfragmented. For
              example a 1500 by L2 frame would configure 1518 when using 
              one VLAN tag. (1500+6+6+2+4). The system will add another 2
              octets to enable full encapsulation of the 1518 octets.";
            reference
             "20.13.6.1, 20.13.7.1 of IEEE 802.1AEdk";
          } 
        }
        list channel {
         key "channel-id";
          description
            "List of Channels supported with their corresponding
             per channel configuration Note both channles are
             forced to be configured";
          reference
            "20.13.6 of IEEE 802.1AEdk";
          leaf channel-id {
            type identityref {
              base channel-identity;
            }
          }
          leaf enabled {
            type boolean;
            default false;
            description
              "A channel may be defined but not active. If no channles are
              active the express and preeemptable traffic is not privacy 
              protected. This allows the enabling and disabling of channels 
              with maintaing the traffic properties";
          }
          leaf access-priority {
            type dot1q-types:priority-type;
            description
              "Priority of the frames mapped to this channel. ";
            reference
                "20.13.6.2, 20.13.7.2 of IEEE 802.1AEdk";
          }
          leaf user-data-frame-size {
            type uint16 {
              range "128 .. 9100";
            }
            units octets;
            default 1518;
            description
              "The maximum size in octets of layer 2 frames that may be
              transmitted or received on the interface (excluding any FCS
              overhead). This size is what you would expect to be capable to 
              carry a single l2 maximum user size frame unfragmented. For
              example a 1500 by L2 frame would configure 1518 when using 
              one VLAN tag. (1500+6+6+2+4).";
            reference
             "20.13.6.1, 20.13.7.1 of IEEE 802.1AEdk";
          } 
          leaf user-data-burst-size {
            type uint32;
            mandatory true;
            description
              "The number of burst octets for traffic traffic that allows an average
               rate of interval packets. The manageable variable burst-size is 
               always greater than or equal to the maxMppduPayloadSize";
            reference
              "20.13.6.5 of IEEE 802.1AEdk";
          }
          leaf requested-bit-rate {
            type uint64;
            units "bit/s";
            mandatory true;
            description
              "Requested Bit-rate in bps for the stream of MAC Privacy packets.
              Time interval for sending frames is the bit rate divided
              by the frame size.This can never be faster than the link speed.";
            reference
              "20.13.6.3 of IEEE 802.1AEdk";
          }
          leaf channel-frame-size  {
            type uint16; 
            units "octets";
            config false;
            description
              "Actual size of the frame on the wire with all overhead.
              This can be used to help calculate accurate intervals.";
            reference
              "20.13.6.6 of IEEE 802.1AEdk)";
          }
          leaf channel-burst-size  {
            type uint32;
            config false;
            description
              "TBD";
            reference
              "20.13.6.6 of IEEE 802.1AEdk)";
          }
          leaf actual-bit-rate {
            type uint64;
            units "octets";
            config false;
            description
              "Bitrate in bps for the stream of MAC Privacy packets.
               This is computed using the actual interval times the 
               effective frame size including all overhead. A system
               computes this value value adding the overhead on top 
               of max-mppdu-payload-size.";
            reference
              "20.13.6.4 of IEEE 802.1AEdk";
          }
        }
      }
      container channel-stats {
        description
          "Channel Transmission stats.";
        leaf out-user-protected-frames {
          type yang:counter64;
          config false;
          description
            "Total number of MAC Privacy user frames sent on a channel.";
          reference
            "20.13.8 of IEEE 802.1AEdk";
        }
        leaf out-user-protected-octets {
          type yang:counter64;
          config false;
          description
            "Total number of MAC Privacy user octets sent on a channel. Does not
            include padding";
          reference
            "20.13.8 of IEEE 802.1AEdk";
        }
        leaf out-encapsulated-frames {
          type yang:counter64;
          config false;
          description
            "Total number of unfragmetned MAC Privacy fragments sent.";
          reference
            "20.13.8 of IEEE 802.1AEdk";
        }
        leaf out-express-fragments {
          type yang:counter64;
          config false;
          description
            "Total number of express MAC Privacy fragments sent. There may be
	     two or more fragments per frame.";
          reference
            "20.13.8 of IEEE 802.1AEdk";
        }
        leaf out-preemptable-fragments {
          type yang:counter64;
          config false;
          description
            "Total number of preemptable MAC Privacy fragments sent. There may be
	     two or more fragments per frame.";
          reference
            "20.13.8 of IEEE 802.1AEdk";
        }
        leaf out-pad-octets {
          type yang:counter64;
          config false;
          description
            "Total number of MAC Privacy padding octets sent.";
          reference
            "20.13.8 of IEEE 802.1AEdk";
        }
        leaf out-mppdus {
          type yang:counter64;
          config false;
          description
            "Total number of MAC Privacy PDUs sent.";
          reference
            "20.13.8 of IEEE 802.1AEdk";
        }
      }
      container frame-stats {
        description
          "Frame Transmission stats.";
        leaf out-encapsulated-frames {
          type yang:counter64;
          config false;
          description
            "Total number of MAC Privacy user frames sent.";
          reference
            "20.13.8 of IEEE 802.1AEdk";
        }
        leaf out-user-protected-octets {
          type yang:counter64;
          config false;
          description
            "Total number of MAC Privacy user octets sent. Does not
            include padding";
          reference
            "20.13.8 of IEEE 802.1AEdk";
        }
        leaf out-pad-octets {
          type yang:counter64;
          config false;
          description
            "Total number of MAC Privacy frame padding octets sent.";
          reference
            "20.13.8 of IEEE 802.1AEdk";
        }
      }
      container unprotected-frame-stats {
        description
          "Frame Transmission stats.";
        leaf out-user-frames {
          type yang:counter64;
          config false;
          description
            "Total number of MAC Privacy user frames sent.";
          reference
            "20.13.8 of IEEE 802.1AEdk";
        }
        leaf out-user-octets {
          type yang:counter64;
          config false;
          description
            "Total number of MAC Privacy user octets sent. Does not
            include padding";
          reference
            "20.13.8 of IEEE 802.1AEdk";
        }
      }
    }
  }
}
