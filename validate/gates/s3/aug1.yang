module aug1 {
   yang-version "1.1";
   namespace
      urn:ieee:exp:yang:aug1;
   prefix a1;
   import main {
      prefix m;
   }
   organization
      "IEEE";
   contact
      "IEEE";
   description
      "augment test must statement impact";
   revision 2021-10-12 {
      description
         "aug1 test";
   }

   augment "/m:main-container/m:main-list" {

      leaf tsn-type {
         type string;
         default "tsn-off";
      }

      container admin-control-list {
         when "../a1:tsn-type = 'tsn-on'";

         list gate-control-entry {
            key "index";
            leaf index {
               type uint32;
            }
            leaf gce-leaf1 {
               type string;
            }
         }
         leaf augleaf1 {
            type string;
         }


         must "(count(./gate-control-entry) > 0)" {
            error-message "admin-control-list empty.";
         }
      }
   }
}
