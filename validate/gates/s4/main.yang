module main {
   yang-version "1.1";
   namespace
      urn:ieee:exp:yang:main;
   prefix m;
   organization
      "IEEE";
   contact
      "IEEE";
   description
      "test main, augments and must statements";
   revision 2021-11-18 {
      description
         "main test";
   }

   container main-container {
      description "main container";
      list main-list {
         key "leaf1";
         leaf leaf1 {
            type string;
         }

         leaf leaf2 {
            type string;
         }
      }
   }
}
