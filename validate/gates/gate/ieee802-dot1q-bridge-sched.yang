module ieee802-dot1q-bridge-sched {
  namespace urn:ieee:std:802.1Q:yang:ieee802-dot1q-bridge-sched;
  prefix bridge-sched;
  
  import ietf-interfaces {
    prefix if;
  }
  import ieee802-dot1q-bridge {
    prefix dot1q;
  }

  import ieee802-dot1q-sched {
    prefix sched;
  }
  organization
    "IEEE 802.1 Working Group";
  contact
    "WG-URL: http://www.ieee802.org/1/
    WG-EMail: stds-802-1-l@ieee.org

    Contact: IEEE 802.1 Working Group Chair
    Postal: C/O IEEE 802.1 Working Group
    IEEE Standards Association
    445 Hoes Lane
    Piscataway, NJ 08854
    USA

    E-mail: STDS-802-1-CHAIRS@IEEE.ORG";
  description
    "This module provides for management of IEEE Std 802.1Q Bridges
    that support Scheduled Traffic Enhancements.";
  
  revision 2021-02-02 {
    description
      "Published as part of IEEE Std 802.1Qcw.
      Initial version.";
    reference
      "IEEE Std 802.1Qcw - Bridges and Bridged Networks — Amendment: 
      YANG Data Models for Scheduled Traffic, Frame Preemption, and 
      Per-Stream Filtering and Policing.";
  }
  

  augment "/if:interfaces/if:interface/dot1q:bridge-port" {
    
    description
      "Augment bridge-port with Scheduled Traffic configuration.";
    
   uses sched:sched-parameters;
  }
}
