module ieee802-dot1ae-pry {
  yang-version "1.1";
  namespace urn:ieee:std:802.1AE:yang:ieee802-dot1ae-pry;
  prefix dot1ae-pry;
  import ietf-interfaces {
    prefix if;
  }
  import ietf-yang-types {
    prefix yang;
  }
  import ieee802-dot1q-types {
    prefix dot1q-types;
  }
  import ieee802-types {
    prefix ieee;
  }
    import iana-if-type {
    prefix ianaift;
  }

  organization
   "IEEE 802.1 Working Group";
  contact
    "WG-URL: http://ieee802.org/1/
    WG-EMail: stds-802-1-l@ieee.org
    
    Contact: IEEE 802.1 Working Group Chair
    Postal: C/O IEEE 802.1 Working Group
           IEEE Standards Association
           445 Hoes Lane
           Piscataway, NJ 08855
           USA
    
    E-mail: stds-802-1-chairs@ieee.org";
  description
    "This YANG module augments the configuration and operational state
    data for interfaces for the MAC Privacy project. IEEE 802.1AEdk";
  revision 2021-06-21 {
    description
      "Initial revision.";
  }
  
  /*--------------------*/
  /* Feature            */
  /*--------------------*/
  feature macsec-priv {
    description
      "Feature MAC Privacy";
  }
  
  /*--------------------*/
  /*   identities       */
  /*--------------------*/
  identity priority-map-identity {
    description
      "Base identity for assigning a priority to a Privacy type";
  }
  identity channel-identity {
    description
      "Base identity for privacy channel";
  }
  identity express-channel {
    base channel-identity;
    base priority-map-identity;
    description
      "This is the express privacy channel frame designation.";
    reference
      "20.13.4 of IEEE 802.1AEdk";
  }
  identity preemptable-channel {
    base channel-identity;
    base priority-map-identity;
    description
      "This is the preemptable privacy channel designation.";
    reference
      "20.13.4 of IEEE 802.1AEdk";
  }
  identity frame-identity {
    description
      "Base identity for privacy frame";
  }
  identity frame {
    base frame-identity;
    base priority-map-identity;
    description
      "This is a privacy frame. A frame-a must be designated for this
      frame if frame-a mapping is used.";   
    reference 
      "20.13.5.1 of IEEE 802.1AEdk";
  }
  identity none-identity {
    description
      "Base identity for privacy frame";
  }
  identity none {
    base none-identity;
    base priority-map-identity;
    description
      "This is no privacy encapsulation. Frames mapped to this identity
       are forwarded directly without MAC privacy encapsulation.";
    reference
      "20.13.5.1 of IEEE 802.1AEdk";
  }
  
  /*--------------------*/
  /* Configuration Data */
  /*--------------------*/
  augment "/if:interfaces/if:interface" {
    if-feature "macsec-priv";
    description
      "MACsec Privacy Mode";
    when
      "if:type = 'ianaift:ethernetCsmacd' or if:type = "+
      "'ianaift:ilan' or if:type = 'ianaift:macSecControlledIF' or "+
      "if:type = 'ianaift:ptm' or if:type = 'ianaift:bridge'" {
      description
        "Augment interfaces with 802.1ae MACSec System specific
        configuration nodes.";
    }
    container pry {
      description
        "Configure the MAC Privacy Options";
      leaf mac-privacy-enabled {
        type boolean; 
        default true;
        description
          "MACSec Privacy Enable - True or False.";
        reference
          "20.13.1 of IEEE 802.1AEdk";
      }
      leaf pry-source-address {
        type ieee:mac-address;
        config false;
        description
          "The individual MAC address of the MAC Privacy service. 
          This address is read only and determined by the system.  
          Normally it is shared with PAE";
        reference
          "20.13.2 of IEEE 802.1AEdk)";
      }
      leaf use-pae-dest-address {
        type boolean;
        default true; 
        description
          "When set to true the destination address used by this 
          PRY is shared with the PAE. When set to false a configured
          destination may override the system MAC address.";
        reference
          "20.13.6.7 of IEEE 802.1AEdk";
      }
      leaf pry-destination-address {
        when "../dot1ae-pry:use-pae-dest-address='false'";
        type ieee:mac-address;
        description
          "The individual or group MAC address of the MAC Privacy
          service. This MAC identifies one or more destinations
          and is normally the address shared with PAE. It may 
          be configured to another address when use-pae-dest-address 
          is set to false";
        reference
          "20.13.3 of IEEE 802.1AEdk";
      }
      list user-priority-to-pry {
        key "user-priority";
        description
          "User priority is mapped to privacy channels express or preemptable
          or to privacy frames";
        reference
          "";
        leaf user-priority {
          type uint8 {
            range "0..7";
          }
          description
            "There are eight values of User Priority that map to ether a
            priority channel or a priority frame.";
          reference
            "20.13.5.1 of IEEE 802.1AEdk";
        }
        leaf privacy-type {
          type identityref {
            base priority-map-identity;
          }
          mandatory true;
          description
            "An identity associated with the privacy channel or frame.";
          reference
            "20.13.5.1 of IEEE 802.1AEdk";
        }
        leaf frame-access-priority {
          when "../dot1ae-pry:privacy-type='dot1ae-pry:frame'";
          type dot1q-types:priority-type;
          description
            "Access Priority of the frames that are mapped to 
             the Frame table";
          reference
              "20.13.6.2, 20.13.7.2 of IEEE 802.1AEdk";
        }
        leaf frame-de-bit-visible {
          when "../dot1ae-pry:privacy-type='dot1ae-pry:frame'";
          type enumeration {
            enum hidden {
              value 0;
            }
            enum visible {
              value 1;
            }
          }
          default hidden;
          description
            "For privacy frames only, this parameter allows Privacy frames 
             with transmitt discard elegible set to be visible and
             set on the encapsualted frame. ";
          reference
              "20.13.6.2, 20.13.7.2 of IEEE 802.1AEdk";
        }
        leaf frame-nearest-multiple-pad {
          when "../dot1ae-pry:privacy-type='dot1ae-pry:frame'";
          type uint16 {
             range "0|16|32|64";
          }
          default 64;
          description
            "The nearest Multiple boundary for padding. Zero is an 
            unpadded frame.  The maximum size in octets of layer 2
            frames that may be transmitted or received on the
            interface (excluding any FCS overhead). Padding is
            add up to a boundary. In the case of Ethernet 
            interfaces it also excludes the 4-8 byte overhead
            of any known (i.e. explicitly matched by a child
            sub-interface) 802.1Q VLAN tags."; 
          reference
            "20.13.7.3 of IEEE 802.1AEdk";
        }
      }
      list channel {
       key "channel-id";
        description
          "List of Channels supported with their corresponding
           per channel configuration Note both channles are
           forced to be configured";
        reference
          "20.13.6 of IEEE 802.1AEdk";
        leaf channel-id {
          type identityref {
            base channel-identity;
          }
        }
        leaf access-priority {
          type dot1q-types:priority-type;
          description
            "Priority of the frames mapped to this channel. ";
          reference
              "20.13.6.2, 20.13.7.2 of IEEE 802.1AEdk";
        }
        leaf user-data-frame-size {
          type uint16 {
            range "128 .. 9100";
          }
          units octets;
          default 1518;
          description
            "The maximum size in octets of layer 2 frames that may be
            transmitted or received on the interface (excluding any FCS
            overhead). This size is what you would expect to be capable to 
            carry a single l2 maximum user size frame unfragmented. For
            example a 1500 by L2 frame would configure 1518 when using 
            one VLAN tag. (1500+6+6+2+4).";
          reference
           "20.13.6.1, 20.13.7.1 of IEEE 802.1AEdk";
        } 
        leaf requested-bit-rate {
          type uint64;
          units "bit/s";
          mandatory true;
          description
            "Requested Bit-rate in bps for the stream of MAC Privacy packets.
            Time interval for sending frames is the bit rate divided
            by the frame size.This can never be faster than the link speed.";
          reference
            "20.13.6.3 of IEEE 802.1AEdk";
        }
        leaf actual-bit-rate {
          type uint64;
          units "octets";
          config false;
          description
            "Bitrate in bps for the stream of MAC Privacy packets.
             This is computed using the actual interval times the 
             effective frame size including all overhead. A system
             computes this value value adding the overhead on top 
             of max-mppdu-payload-size.";
          reference
            "20.13.6.4 of IEEE 802.1AEdk";
        }
        leaf burst-size {
          type uint32;
          mandatory true;
          description
            "The number of burst octets for traffic traffic that allows an average
             rate of interval packets. The manageable variable burst-size is 
             always greater than or equal to the maxMppduPayloadSize";
          reference
            "20.13.6.5 of IEEE 802.1AEdk";
        }
        leaf total-size-on-wire  {
          type uint16; 
          units "octets";
          config false;
          description
            "Actual size of the frame on the wire with all overhead.
            This can be used to help calculate accurate intervals.";
          reference
            "20.13.6.6 of IEEE 802.1AEdk)";
        }
        leaf fragment-enable {
          type boolean;
          config true;
          default true; 
          description
            "Fragmentation control for this channel. It is recommended 
             to use fragmentation at all times for efficiency and minimizing 
             delay. This control allows for showing the effects of fragmentation
             vs no fragmentation or simple performance tests.";
          reference
            "20.13.6.7 of IEEE 802.1AEdk";
        }
      }
      container frame {
        presence "Common Frame size";
        description
          "Frame attributes";
        reference
          "20.13.6.6 of IEEE 802.1AEdk";
        leaf user-data-frame-size {
          type uint16 {
            range "128 .. 9100";
          }
          units octets;
          default 1518;
          description
            "The maximum size in octets of layer 2 frames that may be
            transmitted or received on the interface (excluding any FCS
            overhead). This size is what you would expect to be capable to 
            carry a single l2 maximum user size frame unfragmented. For
            example a 1500 by L2 frame would configure 1518 when using 
            one VLAN tag. (1500+6+6+2+4). The system will add another 2
            octets to enable full encapsuatltion of the 1518 octets.";
          reference
           "20.13.6.1, 20.13.7.1 of IEEE 802.1AEdk";
        } 
      }
      leaf out-mppdus {
        type yang:counter64;
        config false;
        description
          "Total number of MAC Privacy PDUs sent.";
        reference
          "20.13.8 of IEEE 802.1AEdk";
      }
      leaf out-user-frames {
        type yang:counter64;
        config false;
        description
          "Total number of MAC Privacy user frames sent.";
        reference
          "20.13.8 of IEEE 802.1AEdk";
      }
      leaf out-user-octets {
        type yang:counter64;
        config false;
        description
          "Total number of MAC Privacy user octets sent. Does not
          include padding";
        reference
          "20.13.8 of IEEE 802.1AEdk";
      }
      leaf out-pad-octets {
        type yang:counter64;
        config false;
        description
          "Total number of MAC Privacy padding octets sent.";
        reference
          "20.13.8 of IEEE 802.1AEdk";
      }
      leaf out-user-fragments {
        type yang:counter64;
        config false;
        description
          "Total number of MAC Privacy fragments sent.";
        reference
          "20.13.8 of IEEE 802.1AEdk";
      }
      leaf in-mppdus {
        type yang:counter64;
        config false;
        description
          "Total number fo MAC Privacy PDUs received.";
        reference
          "20.13.8 of IEEE 802.1AEdk";
      }
      leaf in-errored-mppdus {
        type yang:counter64;
        config false;
        description
          "Total number of MAC Privacy PDUs dropped due to errors.";
        reference
          "20.13.8 of IEEE 802.1AEdk";
      }
      leaf in-user-frames {
        type yang:counter64;
        config false;
        description
          "Total number of MAC Privacy user frames received.";
        reference
          "20.13.8 of IEEE 802.1AEdk";
      }
      leaf in-errored-user-frames {
        type yang:counter64;
        config false;
        description
          "Total number of MAC Privacy user frames received.";
        reference
          "20.13.8 of IEEE 802.1AEdk";
      }
      leaf in-user-octets {
        type yang:counter64;
        config false;
        description
          "Total number of MAC Privacy user octets received. Does not
          include padding";
        reference
          "20.13.8 of IEEE 802.1AEdk";
      }
      leaf in-pad-octets {
        type yang:counter64;
        config false;
        description
          "Total number of MAC Privacy pad octets received.";
        reference
          "20.13.8 of IEEE 802.1AEdk";
      }
      leaf in-user-complete-fragments {
        type yang:counter64;
        config false;
        description
          "Total number of MAC Privacy fragments that are part of complete 
          frames received with no errors. This statistic does not include
          fragments recieved that are dropped.";
        reference
          "20.13.8 of IEEE 802.1AEdk";
      }
      leaf in-user-dropped-fragments {
        type yang:counter64;
        config false;
        description
          "Total number of MAC Privacy fragmented frames dropped due to
          missing information. This can be due to one or more missing
          fragments or fragments out of order. Only one error is counted
          if anything prevents reassembling a fragmented frame.";
        reference
          "20.13.8 of IEEE 802.1AEdk";
      }
      leaf in-user-errored-fragments {
        type yang:counter64;
        config false;
        description
          "Total number of MAC Privacy PDU fragments dropped due to
          errors.";
        reference
          "20.13.8 of IEEE 802.1AEdk";
      }
    }
  }
}
