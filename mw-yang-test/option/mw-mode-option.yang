module mw-mode-option {
   yang-version "1.1";
   namespace
      urn:ietf:exp:yang:mw-mode-option;
   prefix mmo-exp;
   import ietf-network {
      prefix "nw";
   }
   import ietf-network-topology {
      prefix "nt";
   }
   import ietf-te-topology {
      prefix "tet";
   }
   import ietf-microwave-topology {
      prefix mwtopo;
   }
   organization
      "IETF";
   contact
      "IETF";
   description
      "Example option for new MW mode";
   revision 2022-05-12 {
      description
         "Example MW Mode Option";
   }

   augment "/nw:networks/nw:network/nt:link/tet:te/tet:te-link-attributes/mwtopo:mw-link-choice/mwtopo:mw-link-option/mwtopo:microwave-radio-link/mwtopo:microwave-radio-link" {
      description "Augment to provide example of new mode option";
      container mode-option {
         description "Container that provides flexible definition of number of bonded carriers and protecting carriers";
         leaf num-bonded-carriers {
            type uint32;
            description "Number of bonded carriers";
         }
         leaf num-protecting-carriers {
            type uint32;
            description "Number of protecting carriers";
         }
      }
   }
}
