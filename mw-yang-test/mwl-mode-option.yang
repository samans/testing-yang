module mwl-mode-option {
   yang-version "1.1";
   namespace
      urn:ietf:exp:yang:mwl-mode-option;
   prefix mwlm;
   import ietf-interfaces {
      prefix "if";
   }
   organization
      "IETF";
   contact
      "IETF";
   description
      "Example option for new MW mode";
   revision 2022-05-12 {
      description
         "Example MW Mode Option";
   }

   augment "/if:interfaces/if:interface" {
      description "Augment to provide example of new mode option for microwave radio link";
      container mode-option {
         description "Container that provides flexible definition of number of bonded carriers and protecting carriers";
         leaf num-bonded-carriers {
            type uint32;
            description "Number of bonded carriers";
         }
         leaf num-protecting-carriers {
            type uint32;
            description "Number of protecting carriers";
         }
      }
   }
}
