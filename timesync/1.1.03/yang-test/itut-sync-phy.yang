module itut-sync-phy {
  yang-version 1.1;
  namespace "urn:itu:t:rec:sync-ne:yang:itut-sync-phy";
  prefix sync-phy;

  import ietf-interfaces {
    prefix if;
    reference
      "IETF RFC 8343";
  }

  organization
    "ITU-T Study Group 15 (SG15) - International Telecommunication
    Union";
  contact
    "tsbsg15@itu.int";
  description
    "This module defines a YANG data model for configuring the
    SyncPhy defined in ITU-T G.781.

    The model fully conforms to the Network Management Datastore
    Architecture (NMDA).
   
    Copyright(C) ITU (2025).
     
    All rights reserved. This version of this YANG module is part of
    ITU-T G.7721.1 Data model of synchronization management; see the
    Recommendation itself for full legal notices.";
  /* Note to TSB: replace (YY/2025) through the whole model with the
     actual approval date of G.781 v5.2 and remove this note. */
  reference
    "ITU-T G.781 v5.2 (YY/2025)";

  /* Note to TSB: update the revision date with actual approval date
     of G.7721.1 v2.0 and remove this note */
  /* Note to TSB: replace (XX/2025) through the whole model with the
     actual approval date of G.7721.1 v2.0 and remove this note. */
  revision 2025-04-28 {
    description
      "Initial version.";
    reference
      "ITU-T G.7721.1 v2.0 (XX/2025)";
  }

  /*
  * Feature statements
  */

  feature eql-tlv {
    description
      "This feature means that the the extended Quality Level (eQL)
      TLV is implemented.";
  }

  /*
  * Typedef statements
  */

  typedef port-ref {
    type leafref {
      path "/sync-phy:sync-phy/sync-phy:ports/sync-phy:port"
         + "/sync-phy:underlying-interface";
    }
    description
      "A data type to reference SyncPhy Ports.";
  }

  // III.5.1.31  SyncPhyClockIdentity datatype
  typedef clock-identity {
    type string {
      pattern "[0-9A-F]{2}(-[0-9A-F]{2}){7}";
    }
    description
      "The unique identity of a SyncPhy Clock.";
    reference
      "ITU-T G.781 v5.2 (YY/2025):  annex B.2.1
       ITU-T G.8264 v3.2 (01/2024): clause 11.3.1.3";
  }

  // III.5.1.39  SyncPhyOption_I_QualityLevel enumeration
  typedef option-I-quality-level {
    type enumeration {
      enum eprtc {
        value 0;
        description
          "Timing quality generated by an enhanced primary reference
          time clock (QL-ePRTC).";
      }
      enum prtc {
        value 1;
        description
          "Timing quality generated by a primary reference time clock
          (QL-PRTC).";
      }
      enum eprc {
        value 2;
        description
          "Timing quality generated by an enhanced primary reference
          clock (QL-ePRC).";
      }
      enum prc {
        value 3;
        description
          "Timing quality generated by a primary reference clock
          (QL-PRC).";
      }
      enum ssu-a {
        value 4;
        description
          "Timing quality generated by a type I or V clock
          (QL-SSU-A).";
      }
      enum ssu-b {
        value 5;
        description
          "Timing quality generated by a type VI clock (QL-SSU-B).";
      }
      enum esec {
        value 6;
        description
          "Timing quality generated by an enhanced synchronous
          equipment clock (QL-eSEC).";
      }
      enum sec {
        value 7;
        description
          "Timing quality generated by a synchronous equipment clock
          (QL-SEC).";
      }
      enum dnu {
        value 16;
        description
          "A quality level (QL) indicating that the signal should not
          be used for synchronization (QL-DNU).";
      }
      enum inv {
        value 17;
        description
          "An internal quality level (QL) generated when an
          unallocated synchronization status message (SSM) value is
          received or when an allocated SSM value and an unallocated
          enhanced SSM (eSSM) value are received (QL-INV).";
      }
      enum failed {
        value 18;
        description
          "An internal quality level (QL) generated when the
          Synchronization Distribution (SD) trail is in the signal
          fail state (QL-FAILED).";
      }
      enum unc {
        value 19;
        description
          "An internal quality level (QL) generated when the output
          signal is not connected to an input, but instead to the
          internal unconnected signal generator  (QL-UNC).";
      }
      enum nsupp {
        value 20;
        description
          "An internal quality level (QL) generated when the function
          is not supporting the synchronization status message (SSM)
          or the timing marker (TM) processing (QL-NSUPP).";
      }
    }
    description
      "The quality level of a clock with network option I.";
    reference
      "ITU-T G.781 v5.2 (YY/2025): table B.1; clause 5.4.1.1 and
                                   clause 5.4.2.1.";
  }

  // III.5.1.38  SyncPhyOption_II_QualityLevel enumeration
  typedef option-II-quality-level {
    type enumeration {
      enum eprtc {
        value 32;
        description
          "Timing quality generated by an enhanced primary reference
          time clock (QL-ePRTC).";
      }
      enum prtc {
        value 33;
        description
          "Timing quality generated by a primary reference time clock
          (QL-PRTC).";
      }
      enum eprc {
        value 34;
        description
          "Timing quality generated by an enhanced primary reference
          clock (QL-ePRC).";
      }
      enum prs {
        value 35;
        description
          "Primary Reference Source (PRS) traceable (QL-PRS).";
      }
      enum stu {
        value 36;
        description
          "Synchronized - Traceability unknown (QL-STU).";
      }
      enum st2 {
        value 37;
        description
          "Traceable to stratum 2 (QL-ST2).";
      }
      enum tnc {
        value 38;
        description
          "Traceable to transit node clock (QL-TNC).";
      }
      enum st3e {
        value 39;
        description
          "Traceable to stratum 3E (QL-ST3E).";
      }
      enum esec {
        value 40;
        description
          "Traceable to an enhanced synchronous equipment clock
          (QL-eSEC).";
      }
      enum st3 {
        value 41;
        description
          "Traceable to stratum 3 (QL-ST3).";
      }
      enum smc {
        value 42;
        description
          "Traceable to SONET clock self timed (QL-SMD).";
      }
      enum st4 {
        value 43;
        description
          "Traceable to stratum 4 free-run (QL-ST4).";
      }
      enum prov {
        value 44;
        description
          "A quality level (QL) provisionable by the operator
          (QL-PROV).";
      }
      enum dus {
        value 48;
        description
          "A quality level (QL) indicating that the signal should not
          be used for synchronization (QL-DSU).";
      }
      enum inv {
        value 49;
        description
          "An internal quality level (QL) generated when an
          unallocated synchronization status message (SSM) value is
          received or when an allocated SSM value and an unallocated
          enhanced SSM (eSSM) value are received (QL-INV).";
      }
      enum failed {
        value 50;
        description
          "An internal quality level (QL) generated when the
          Synchronization Distribution (SD) trail is in the signal
          fail state (QL-FAILED).";
      }
      enum unc {
        value 51;
        description
          "An internal quality level (QL) generated when the output
          signal is not connected to an input, but instead to the
          internal unconnected signal generator  (QL-UNC).";
      }
      enum nsupp {
        value 52;
        description
          "An internal quality level (QL) generated when the function
          is not supporting the synchronization status message (SSM)
          or the timing marker (TM) processing (QL-NSUPP).";
      }
    }
    description
      "The quality level of a clock with network option II.";
    reference
      "ITU-T G.781 v5.2 (YY/2025): table B.1; clause 5.4.1.2 and
                                   clause 5.4.2.2.";
  }

  // III.5.1.37  SyncPhyOption_III_QualityLevel enumeration
  typedef option-III-quality-level {
    type enumeration {
      enum eprtc {
        value 64;
        description
          "Timing quality generated by an enhanced primary reference
          time clock (QL-ePRTC).";
      }
      enum prtc {
        value 65;
        description
          "Timing quality generated by a primary reference time clock
          (QL-PRTC).";
      }
      enum unk {
        value 66;
        description
          "Timing quality generated by an unknown clock source
          (QL-UNK).";
      }
      enum esec {
        value 67;
        description
          "Timing quality generated by an enhanced synchronous
          equipment clock (QL-eSEC).";
      }
      enum sec {
        value 68;
        description
          "Timing quality generated by a synchronous equipment clock
          (QL-SEC).";
      }
      enum inv {
        value 80;
        description
          "An internal quality level (QL) generated when an
          unallocated synchronization status message (SSM) value is
          received (QL-INV).";
      }
      enum failed {
        value 81;
        description
          "An internal quality level (QL) generated when the
          Synchronization Distribution (SD) trail is in the signal
          fail state (QL-FAILED).";
      }
      enum unc {
        value 82;
        description
          "An internal quality level (QL) generated when the output
          signal is not connected to an input, but instead to the
          internal unconnected signal generator  (QL-UNC).";
      }
      enum nsupp {
        value 83;
        description
          "An internal quality level (QL) generated when the function
          is not supporting the synchronization status message (SSM)
          or the timing marker (TM) processing (QL-NSUPP).";
      }
    }
    description
      "The quality level of a clock with network option III.";
    reference
      "ITU-T G.781 v5.2 (YY/2025): table B.1; clause 5.4.1.3 and
                                   clause 5.4.2.3.";
  }

  // III.5.1.44  SyncPhyQualityLevel datatype
  typedef quality-level {
    type union {
      type option-I-quality-level;
      type option-II-quality-level;
      type option-III-quality-level;
    }
    description
      "The quality level of a clock.

      The network option qualifies whether the type is an Option I,
      an Option II or an Option III quality level.";
    reference
      "ITU-T G.781 v5.2 (YY/2025): annex B.2.2";
  }

  // III.5.1.46  SyncPhySaBit
  typedef sa-bit {
    type enumeration {
      enum sa4 {
        value 4;
        description
          "Sa bit 4.";
      }
      enum sa5 {
        value 5;
        description
          "Sa bit 5.";
      }
      enum sa6 {
        value 6;
        description
          "Sa bit 6.";
      }
      enum sa7 {
        value 7;
        description
          "Sa bit 7.";
      }
      enum sa8 {
        value 8;
        description
          "Sa bit 8.";
      }
    }
    description
      "The Sa bit of a SyncPhy Port which is used to carry the
      Synchronization Status Message (SSM) codes.";
    reference
      "ITU-T G.781 v5.2 (YY/2025): annex B.2.4 and table B.2.";
  }

  /* 
   * Data definition statements
   */
  
  container sync-phy {
    description
      "Top level container for the configuration and state of a
       SyncPhy Instance.";
    container default-ds {
      description
        "The Default data set (DS) of the SyncPhy Instance.";
      reference
        "ITU-T G.781 v5.2 (YY/2025): annex B.3";
      leaf clock-identity {
        type clock-identity;
        config false;
        description
          "The identity of the system clock.
          
          When the the extended Quality Level (eQL) TLV is
          implemented, this attribute is mandatory. Otherwise,
          it is optional.";
        reference
          "ITU-T G.781 v5.2 (YY/2025): annex B.3.2";
      }
      leaf quality-level {
        type quality-level;
        config false;
        description
          "The Synchronization Status Message (SSM) quality level of
          the clock of the NE.";
        reference
          "ITU-T G.781 v5.2 (YY/2025): annex B.3.3";
      }
      leaf eql-sel {
        // III.5.1.34  SyncPhyEqlSel
        type boolean;
        description
          "Indicates whether the information of the extended Quality
          Level (eQL) TLV is used by the source selection
          algorithm.
          
          When set to true, the eQL TLV is used.
          
          When set to false, the eQL TLV is not used.
          
          When the the extended Quality Level (eQL) TLV is
          implemented, this attribute is mandatory. Otherwise,
          it is optional.";
        reference
          "ITU-T G.781 v5.2 (YY/2025): annex B.3.4";
      }
      leaf sync-network-option {
        // III.5.1.36  SyncPhyNetworkOption
        type enumeration {
          enum option-I {
            value 0;
            description
              "Network Option I.";
          }
          enum option-II {
            value 1;
            description
              "Network Option II.";
          }
          enum option-III {
            value 2;
            description
              "Network Option III.";
          }
        }
        description
          "The network option of the SynchPhy instance.";
        reference
          "ITU-T G.781 v5.2 (YY/2025): annex B.3.5 and table B.4";
      }
      leaf clock-mode {
        // III.5.1.32  SyncPhyClockMode
        type enumeration {
          enum free-run {
            value 0;
            description
              "Free-run.";
          }
          enum locked {
            value 1;
            description
              "Locked.";
          }
          enum locked-holdover-memory-acquired {
            value 2;
            description
              "Locked, holdover memory acquired.";
          }
          enum holdover {
            value 3;
            description
              "Holdover.";
          }
        }
        config false;
        description
          "The clock mode status of the system clock.";
        reference
          "ITU-T G.781 v5.2 (YY/2025): annex B.3.6 and table B.5";
      }
      leaf time-since-current-clock-mode {
        type uint32;
        units "seconds";
        config false;
        description
          "The time elapsed in the current clock mode.";
        reference
          "ITU-T G.781 v5.2 (YY/2025): annex B.3.13";
      }
      leaf clock-operation {
        // III.5.1.33  SyncPhyClockOperation 
        type enumeration {
          enum normal {
            value 0;
            description
              "Normal operation.";
          }
          enum forced-free-run {
            value 1;
            description
              "Forced Free-run operation.";
          }
          enum forced-holdover {
            value 2;
            description
              "Forced Holdover operation.";
          }
        }
        description
          "The operation mode of the system clock.";
        reference
          "ITU-T G.781 v5.2 (YY/2025): annex B.3.7 and table B.6";
      }
      leaf source-switch-type {
        // III.5.1.49  SyncPhySwitchType
        type enumeration {
          enum auto {
            value 0;
            description
              "Automatic selection type.";
          }
          enum manual {
            value 1;
            description
              "Manual selection type.";
          }
          enum forced {
            value 2;
            description
              "Forced selection type.";
          }
        }
        description
          "The switch selection type for the system clock.";
        reference
          "ITU-T G.781 v5.2 (YY/2025): annex B.3.8 and table B.7.";
      }
      leaf forced-source {
        when '../sync-phy:source-switch-type = "forced"' {
          description
            "When the switch selection type is forced.";
        }
        type port-ref;
        mandatory true;
        description
          "The SyncPhy Port that is forced to be the source input.";
        reference
          "ITU-T G.781 v5.2 (YY/2025): annex B.3.9";
      }
      leaf manual-source {
        when '../sync-phy:source-switch-type = "manual"' {
          description
            "When the switch selection type is manual.";
        }
        type port-ref;
        mandatory true;
        description
          "The SyncPhy Port that is manually selected as the source
           input.";
        reference
          "ITU-T G.781 v5.2 (YY/2025): annex B.3.10";
      }
      leaf wtr-time {
        type uint8 {
          range "0..12";
        }
        units "minutes";
        default 5;
        description
          "The Wait To Restore (WTR) time.";
        reference
          "ITU-T G.781 v5.2 (YY/2025): annex B.3.11";
      }
      leaf ql-enable {
        type boolean;
        description
          "Indicates whether the quality level is used by the source
          selection of the system clock, or not.";
        reference
          "ITU-T G.781 v5.2 (YY/2025): annex B.3.12";
      }
    } // container default-ds
    container current-ds {
      description
        "The Current data set (DS) of the SyncPhy Instance.";
      reference
        "ITU-T G.781 v5.2 (YY/2025): annex B.4";
      leaf source-port {
        type port-ref;
        config false;
        description
          "The SyncPhy Port selected as reference for the frequency
          system clock currently.";
        reference
          "ITU-T G.781 v5.2 (YY/2025): annex B.4.2";
      }
      leaf mixed-chain {
        if-feature eql-tlv;
        type boolean;
        config false;
        description
          "Indicates whether the SEC/eSEC chain, started from the
          originator of the extended Quality Level (eQL) TLV, is
          composed of only enhanced Synchronous Equipment Clock
          (eSEC) clocks  or of the mixture of SEC and eSEC clocks.
          
          In case the eQL TLV is not received on the port that is
          selected as current reference of the node, the value of
          this attribute is implementation specific.";
        reference
          "ITU-T G.781 v5.2 (YY/2025):  annex B.4.3 and clause 6

           ITU-T G.8264 v3.2 (01/2024): clause 11.3.1.3";
      }
      leaf partial-chain {
        if-feature eql-tlv;
        type boolean;
        config false;
        description
          "Indicates whether the originator of the extended Quality
          Level (eQL) TLV of the SEC/eSEC chain is the clock at the
          head of the chain (i.e., a Synchronization Supply Unit
          (SSU), Primary Reference Clock (PRC) or enhanced PRC
          (ePRC)) or a clock in the middle of the chain.
          
          In case the eQL TLV is not received on the port that is
          selected as current reference of the node, the value of
          this dataset member is implementation specific.";
        reference
          "ITU-T G.781 v5.2 (YY/2025):  annex B.4.4 and clause 6

           ITU-T G.8264 v3.2 (01/2024): clause 11.3.1.3";
      }
      leaf hops-number {
        if-feature eql-tlv;
        type uint8;
        config false;
        description
          "The number of Synchronous Equipment Clock (SEC) nodes from
          the nearest Synchronization Supply Unit (SSU), Primary
          Reference Clock (PRC) or enhanced PRC (ePRC) in the
          synchronization network reference chain.
          
          In case the eQL TLV is not received on the port that is
          selected as current reference of the node, the value of
          this attribute is implementation specific.
          
          Note: the count reported by this attribute is incomplete
          when the SEC/eSEC chain, started from the originator of the
          extended QL TLV, is composed of the mixture of SEC and eSEC
          clocks, as reported by the partial-chain attribute.";
        reference
          "ITU-T G.781 v5.2 (YY/2025):  annex B.4.5

           ITU-T G.8264 v3.2 (01/2024): table 11-5";
      }
      leaf enhanced-hops-number {
        if-feature eql-tlv;
        type uint8;
        config false;
        description
          "The number of enhanced Synchronous Equipment Clock (eSEC)
          nodes from the nearest Synchronization Supply Unit (SSU),
          Primary Reference Clock (PRC) or enhanced PRC (ePRC) in the
          synchronization network reference chain.
          
          In case the eQL TLV is not received on the port that is
          selected as current reference of the node, the value of
          this attribute is implementation specific.
          
          Note: the count reported by this attribute is incomplete
          when the SEC/eSEC chain, started from the originator of the
          extended QL TLV, is composed of the mixture of SEC and eSEC
          clocks, as reported by the partial-chain attribute.";
        reference
          "ITU-T G.781 v5.2 (YY/2025):  annex B.4.6

           ITU-T G.8264 v3.2 (01/2024): table 11-5";
      }
      leaf frequency-offset-from-ck-source {
        type int16;
        units "per part billion (ppb)";
        config false;
        description
          "The frequency offset calculated by the frequency offset
          source performance degradation defect.";
        reference
          "ITU-T G.781 v5.2 (YY/2025): annex B.4.7 and
                                       clause 6.3.1.";
      }
    } // container current-ds
    container parent-ds {
      description
        "The Parent data set (DS) of the SyncPhy Instance.";
      reference
        "ITU-T G.781 v5.2 (YY/2025):  annex B.5";
      leaf system-clock-source-id {
        if-feature eql-tlv;
        type clock-identity;
        config false;
        description
          "The clock identity of the originator of the extended
          Quality Level (eQL) TLV of the system clock.
          
          In case the eQL TLV is not received on the port that is
          selected as current reference of the node, the value of
          this attribute is implementation specific.";
        reference
          "ITU-T G.781 v5.2 (YY/2025): annex B.5.2 and figure 5-6";
      }
      leaf system-clock-source-ql {
        type quality-level;
        config false;
        description
          "The quality level (QL) of the originator of the QL TLV and
          the extended QL (eQL) TLV if supported.";
        reference
          "ITU-T G.781 v5.2 (YY/2025): annex B.5.3 and figure 5-6";
      }
    } // container parent-ds
    container ports {
      description
        "The top level container for the list of SyncPhy Ports.";
      list port {
        key underlying-interface;
        description
          "The list of SyncPhy Ports.";
        leaf underlying-interface {
          type if:interface-ref;
          description
            "Reference to the configured underlying IETF YANG
             interface that is used by this SyncPhy Port.
             Among other data, physical identifiers for the
             interface (e.g., MAC address) can be obtained using
             this reference.";
          reference
            "IETF RFC 8343";
        }
        container port-ds {
          description
            "The Port data set (DS) of the SyncPhy Port.";
          reference
            "ITU-T G.781 v5.2 (YY/2025): annex B.6";
          leaf port-name {
            type string;
            config false;
            description
              "The identity of the SyncPhy Port.
              The format of the port name string is implementation
              specific.";
            reference
              "ITU-T G.781 v5.2 (YY/2025): annex B.6.2.1";
          }
          leaf port-type {
            // III.5.1.41  SyncPhyPortType
            type enumeration {
              enum station-clock {
                value 0;
                description
                  "SyncPhy Station Clock Port.";
              }
              enum line-clock {
                value 1;
                description
                  "SyncPhy Line Clock Port.";
              }          
            }
            config false;
            description
              "The type of the SyncPhy Port.";
            reference
              "ITU-T G.781 v5.2 (YY/2025):  annex B.6.2.2 and
                                            table B.8";
          }
          leaf port-status {
            // III.5.1.40  SyncPhyPortStatus
            type enumeration {
              enum available {
                value 0;
                description
                  "Available state.";
              }
              enum failed {
                value 1;
                description
                  "Failed state.";
              }
              enum wtr {
                value 2;
                description
                  "Wait To Restore (WTR) state.";
              }
              enum hold-off {
                value 3;
                description
                  "Hold-off state.";
              }
            }
            config false;
            description
              "The status of the SyncPhy Port.";
            reference
              "ITU-T G.781 v5.2 (YY/2025):  annex B.6.2.3 and
                                            table B.9";
          }
          leaf lock-out {
            type boolean;
            description
              "The configuration of the Lockout function of the
              SyncPhy Port.
              
              When set to true, the SyncPhy Port is no longer
              considered by the selection process.
              
              When set to false, the SyncPhy Port is able to be
              considered by the selection process.";
            reference
              "ITU-T G.781 v5.2 (YY/2025): annex B.6.2.4";
          }
          leaf ssm-supp {
            type boolean;
            description
              "Indicates whether a SyncPhy Port is configured to
              process the received Synchronization Status Message
              (SSM).

              When set to true, the SyncPhy Port is configured to
              process the received SSM.

              When set to false, the SyncPhy Port is configured not
              to process the received SSM.

              It is only applicable for STM-N, Pqs, type1 P12s and
              type2 P12s interfaces.";
            reference
              "ITU-T G.781 v5.2 (YY/2025): annex B.6.2.5";
          }
          leaf essm-supp {
            if-feature eql-tlv;
            type boolean;
            config false;  
            description
              "Indicates whether a SyncPhy Port supports the ability
              to process the received enhanced Synchronization Status
              Message (eSSM).

              When it is true, the SyncPhy Port supports the ability
              to process the received eSSM.

              When it is false, the SyncPhy Port cannot support the
              ability to process the received eSSM.";
            reference
              "ITU-T G.781 v5.2 (YY/2025): annex B.6.2.6";
          }
          leaf local-priority-for-system-clock {
            type uint8;
            default 0;
            description
              "The priority of the SyncPhy Port that is a candidate
              reference for the system clock.

              A smaller number has a higher priority.

              The value 0 represents that this SyncPhy Port is not
              nominated for the system clock.";
            reference
              "ITU-T G.781 v5.2 (YY/2025): annex B.6.2.7 and
                                           Figure 5-6;
              
               ITU-T G.8264 v3.2 (01/2024): Figure A.2.";
          }
          leaf ssm-send-enable {
            type boolean;
            description
              "Indicates whether the SyncPhy Port is required to send
              Synchronization Status Message (SSM) messages.

              When set to true, the SyncPhy Port is required to send
              SSM messages.

              When set to false, the SyncPhy Port is not allowed to
              send SSM messages.";
            reference
              "ITU-T G.781 v5.2 (YY/2025): annex B.6.2.8";
          }
          leaf ql-input-info {
            type quality-level;
            config false;      
            description
              "The current input Synchronization Status Message (SSM)
              quality levels received at the SyncPhy Port.";
            reference
              "ITU-T G.781 v5.2 (YY/2025): annex B.6.2.9";
          }
          leaf ql-overwrite {
            // III.5.1.43  SyncPhyQlOverwriteMode
            type enumeration {
              enum pass-through {
                value 0;
                description
                  "Quality Level (QL) Pass through mode.";
              }
              enum overwrite {
                value 1;
                description
                  "Quality Level (QL) Overwrite mode.";
              }          
            }  
            description
              "The input Quality Level (QL) mode.";
            reference
              "ITU-T G.781 v5.2 (YY/2025):  annex B.6.2.10 and
                                            table B.10";
          }
          leaf ql-fixed-value {
            when '../sync-phy:ql-overwrite = "overwrite"' {
              description
                "When the Quality Level (QL) overwrite mode is
                configured.";
            }
            type quality-level;
            description
              "The Quality Level (QL) value at input.";
            reference
              "ITU-T G.781 v5.2 (YY/2025): annex B.6.2.11";
          }
          leaf ql-output-info {
            type quality-level;
            config false;      
            description
              "The current output Synchronization Status Message
              (SSM) quality level of the SyncPhy Port.";
            reference
              "ITU-T G.781 v5.2 (YY/2025): annex B.6.2.12";
          }
          leaf ssm-in-sa-bit {
            type sa-bit;
            description
              "The Sa bit of an input SyncPhy Port which is used to
              carry the Synchronization Status Message (SSM) codes.";
            reference
              "ITU-T G.781 v5.2 (YY/2025): annex B.6.2.13";
          }
          leaf ssm-out-sa-bit {
            type sa-bit;
            description
              "The Sa bit of an output SyncPhy Port which is used to
              carry the Synchronization Status Message (SSM) codes.";
            reference
              "ITU-T G.781 v5.2 (YY/2025): annex B.6.2.14";
          }
          leaf wtr-remaining-time {
            type uint16 {
              range "0..720";
            }
            config false;
            description
              "The number of seconds remaining in the Wait To Restore
              (WTR) timer expiry.";
            reference
              "ITU-T G.781 v5.2 (YY/2025): annex B.6.2.15";
          }
          container station-clock-port {
            description
              "The attributes of a SyncPhy Station Clock Port.
               
               This container is applicable only when the SyncPhy
               Port is a Station Clock Port
               (../port-type = 'station-clock').";
            reference
              "ITU-T G.781 v5.2 (YY/2025): annex B.6.3";
            leaf port-type {
              // III.5.1.47  SyncPhyStationClockPortType
              type enumeration {
                enum 2048-kHz {
                  value 0;
                  description
                    "A 2048 kHz SyncPhy Station Clock Port.";
                }
                enum 2048-kbps {
                  value 1;
                  description
                    "A 2048 kbit/s SyncPhy Station Clock Port.";
                }
                enum 1544-kbps {
                  value 2;
                  description
                    "A 1544 kbit/s SyncPhy Station Clock Port.";
                }        
              }
              description
                "The clock type of a SyncPhy Station Clock Port.";
              reference
                "ITU-T G.781 v5.2 (YY/2025):  annex B.6.3.1 and
                                              table B.11";
            }
            leaf ssm-out-threshold {
              type quality-level;
              description
                "The Synchronization Status Message (SSM) quality
                level threshold of the station clock output.";
              reference
                "ITU-T G.781 v5.2 (YY/2025): annex B.6.3.2";
            }
            leaf output-selector {
              // III.5.1.48  SyncPhyStationClockOutputSelector
              type enumeration {
                enum system-clock {
                  value 0;
                  description
                    "The system clock.";
                }
                enum line-clock-port {
                  value 1;
                  description
                    "A line clock port.";
                }        
              }
              description
                "The source of the signal for the station clock
                output (see selector C of Figure A.2).";
              reference
                "ITU-T G.781 v5.2 (YY/2025):  annex B.6.3.3 and
                                              table B.12
                 
                 ITU-T G.8264 v3.2 (01/2024): Figure A.2";
            }
            leaf output-source-port {
              type port-ref;
              config false;
              description
                "The SyncPhy Port selected as reference for the
                station clock output.";
              reference
                "ITU-T G.781 v5.2 (YY/2025): annex B.6.3.4";
            }
            leaf output-source-id {
              if-feature eql-tlv;
              type clock-identity;
              config false;
              description
                "The source clock identity of the station clock
                output, which is derived from the extended Quality
                Level (eQL) TLV of the source.
                
                In case the eQL TLV is not received on the port that
                is selected as current reference of the node, the
                value of this attribute is implementation specific.";
              reference
                "ITU-T G.781 v5.2 (YY/2025): annex B.6.3.5";
            }
            leaf output-source-ql {
              type quality-level;
              config false;
              description
                "The source quality level of the station clock
                output.";
              reference
                "ITU-T G.781 v5.2 (YY/2025): annex B.6.3.6";
            }
          } // container station-clock-port
          container line-clock-port {
            description
              "The attributes of a SyncPhy Line Clock Port.
               
               This container is applicable only when the SyncPhy
               Port is a Line Clock Port
               (../port-type = 'line-clock').";
            reference
              "ITU-T G.781 v5.2 (YY/2025): annex B.6.4";
            leaf line-clock-tm-mode {
              type boolean;
              description
                "Indicates whether to use the Timing Marker (TM) code
                or the Synchronization Status Message (SSM) code.

                When set to true, the TM code is used.

                When set to false, the SSM code is used.

                It is only applicable for Pqs interfaces.";
              reference
                "ITU-T G.781 v5.2 (YY/2025):  annex B.6.4.1.";
            }
          }
        } // container port-ds
      }
    } // container ports
  }
}
