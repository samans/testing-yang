module itut-ptp-tt-telecom-profile {
  yang-version 1.1;
  namespace "urn:itu:t:rec:sync-ne:yang:itut-ptp-tt-telecom-profile";
  prefix ptp-tlp;

  import ieee1588-ptp-tt {
    prefix ptp-tt;
  reference
    "IEEE Std 1588e-2024";
  }

  /* Note to TSB: replace (XX/2024) with actual approval date
    of G.7721.1 v1.1 and remove this note. */
  import itut-ptp-telecom-profile-types {
    prefix ptp-tlp-types;
    reference
      "ITU-T G.7721.1 v1.1 (XX/2024).";
  }

  organization
    "ITU-T Study Group 15 (SG15) Question 14 (Q14/15)";
  contact
    "Q14/15 Web: <https://www.itu.int/en/ITU-T/studygroups/
                  2022-2024/15/Pages/q14.aspx>
    
    Q14/15 List: <t22sg15q14@lists.itu.int>
    
    Editor:      Rongduo (Rod) LU
                 <mailto:lurongduo@chinamobile.com>
    
    Editor:      Bin LUO
                 <mailto:luo.bin5@zte.com.cn>
    
    Editor:      Kam LAM
                 <mailto:kam.lam@fhusainc.com>
    
    Editor:      Scott MANSFIELD
                 <mailto:scott.mansfield@ericsson.com>";
  description
    "This module defines a YANG data model for configuring the
    PTP Telecom Profiles defined in ITU-T G.8265.1, G.8275.1 and
    G.8275.2 by augmenting the PTP-TT YANG model defined in
    IEEE Std 1588e-2024.

    The model fully conforms to the Network Management Datastore
    Architecture (NMDA).

    Copyright (c) 2024 ITU.
     
    All rights reserved. No part of this publication may be
    reproduced, by any means whatsoever, without the prior written
    permission of ITU.";
  /* Note to TSB: replace (Draft) with actual approval date of
     G.8265.1 v4.1, G.8275.1 v4.2 and G.8275.2 v3.2 through all the
     YANG model and remove this note. */
  reference
    "ITU-T G.8265.1 v4.1 (Draft)

    ITU-T G.8275.1 v4.2 (Draft)

    ITU-T G.8275.2 v3.2 (Draft)";

  /* Note to TSB: update the revision date and 
     replace (XX/2024) with actual approval date of
     G.7721.1 v1.1 and remove this note. */
  revision 2024-08-06 {
    description
      "Initial Version.";
    reference
      "ITU-T G.7721.1 v1.1 (XX/2024).";
  }

/*
 * Typedef
 */

  typedef G.8265.1-device-type {
    type enumeration {
      enum packet-time-transmitter {
        description
          "Packet timeTransmitter device type.";
      }
      enum packet-time-receiver {
        description
          "Packet timeReceiver device type.";
      }
    }
    description
      "The device type of a G.8265.1 PTP Telecom Profile Instance.";
    reference
      "ITU-T G.8265.1 v4.1 (Draft): clause 6.2.3.1";
  }

  typedef G.8275.1-device-type {
    type enumeration {
      enum t-gm {
        description
          "Telecom Grandmaster (T-GM) device type.";
      }
      enum t-tsc {
        description
          "Telecom Time Synchronous Clock (T-TSC) device type.";
      }
      enum t-bc {
        description
          "Telecom Boundary Clock (T-BC) device type.";
      }
      enum t-tc {
        description
          "Telecom Transparent Clock (T-TC) device type.";
      }
    }
    description
      "The device type of a G.8275.1 PTP Telecom Profile Instance.";
    reference
      "ITU-T G.8275.1 v4.2 (Draft): clause 6.2.3.1";
  }

  typedef G.8275.2-device-type {
    type enumeration {
      enum t-gm {
        description
          "Telecom Grandmaster (T-GM) device type.";
      }
      enum t-tsc-a {
        description
          "Telecom Time Synchronous Clock for Assisted partial
          timing support (T-TSC-A) device type.";
      }
      enum t-tsc-p {
        description
          "Telecom Time Synchronous Clock for Partial timing support
          (T-TSC-P) device type.";
      }
      enum t-bc-a {
        description
          "Telecom Boundary Clock for Assisted partial timing
          support (T-BC-A) device type.";
      }
      enum t-bc-p {
        description
          "Telecom Boundary Clock for Partial timing support
          (T-BC-P) device type.";
      }
    }
    description
      "The device type of a G.8275.2 PTP Telecom Profile Instance.";
    reference
      "ITU-T G.8275.2 v3.2 (Draft): clause 6.2.3.1";
  }

  /*
   * Groupings
   */

  grouping ptp-tlp-profile-identifier {
    description
      "The identifier of the PTP Telecom Profile.";
    leaf type {
      type ptp-tlp-types:ptp-telecom-profile-type;
      mandatory true;
      description
        "The PTP Telecom Profile.";
    }
    container version {
      description
        "The major and minor version of the PTP Telecom Profile.";
      uses ptp-tlp-types:ptp-profile-version;
    }
    leaf identifier {
      type string;
      config false;
      description
        "The identifier of the PTP Telecom Profile, provided by the
        system based on the PTP Telecom Profile and version.

        It is a string representing 6-octets separated by '-'
        (e.g., 00-19-A7-01-02-06).";
      reference
        "ITU-T G.8265.1 v4.1 (Draft): annex A.1
        
        ITU-T G.8275.1 v4.2 (Draft): annex A.1
        
        ITU-T G.8275.2 v3.2 (Draft): annex A.1";
    }
  }

  /* 
   * Data Nodes
   */

  augment "/ptp-tt:ptp/ptp-tt:instances/ptp-tt:instance"
        + "/ptp-tt:default-ds" {
    description
      "Augment the Default data set (DS) of a PTP Instance.";
    container ptp-telecom-profile {
      presence
        "When present, the PTP Instance is a PTP Telecom Profile
        Instance.

        The conformance level of optional attributes, default
        values and value ranges are defined in the relevant PTP
        Telecom Profile Recommendations, as defined in
        G.7721.1/Annex A.";
      description
        "The additional Default data set (DS) members of the PTP
         Telecom Profile Instance.";
      container profile-identifier {
        description
          "The PTP Telecom Profile which applies to the PTP
          Instance.";
        reference
          "ITU-T G.8265.1 v4.1 (Draft): annex A.1
          
          ITU-T G.8275.1 v4.2 (Draft): annex A.1
          
          ITU-T G.8275.2 v3.2 (Draft): annex A.1";
        uses ptp-tlp-profile-identifier;
      }
      leaf device-type {
        type union {
          type G.8265.1-device-type;
          type G.8275.1-device-type;
          type G.8275.2-device-type;
        }
        mandatory true;
        description
          "The device type for the PTP Telecom Profile Instance.
          
          The profile-identifier qualifies whether the type is a
          G.8265.1 or a G.8275.1 or a G.8275.2 device type.";
        reference
          "ITU-T G.8265.1 v4.1 (Draft): clause 6.2.3.1
          
          ITU-T G.8275.1 v4.2 (Draft): clause 6.2.3.1
          
          ITU-T G.8275.2 v3.2 (Draft): clause 6.2.3.1";
      }
      uses ptp-tlp-types:common-ptp-tlp-default-ds-pac;
      reference
        "ITU-T G.8265.1 v4.1 (Draft): table A.1
        
         ITU-T G.8275.1 v4.2 (Draft): table A.1
         
         ITU-T G.8275.2 v3.2 (Draft): table A.1
         
         ITU-T G.7721.1 v1.1 (XX/2024): Annex A";
    }
  }

  augment "/ptp-tt:ptp/ptp-tt:instances/ptp-tt:instance"
        + "/ptp-tt:ports/ptp-tt:port/ptp-tt:port-ds" {
    description
      "Augment the Port data set (DS) of a PTP Port.";
    container ptp-telecom-profile {
      when ../../../../ptp-tt:default-ds/ptp-telecom-profile {
        description
          "Applies to the PTP Ports of a PTP Telecom Profile
          Instance.";
      }
      description
        "The additional Port data set (DS) members of the PTP Telecom
         Profile Port.";
      uses ptp-tlp-types:common-ptp-tlp-port-ds-pac;
      reference
        "ITU-T G.8265.1 v4.1 (Draft): table A.5
        
         ITU-T G.8275.1 v4.2 (Draft): table A.5
         
         ITU-T G.8275.2 v3.2 (Draft): table A.5";
    }
  }

  augment "/ptp-tt:ptp/ptp-tt:transparent-clock-default-ds" {
    description
      "Augment the Transparent Clock (TC) Default data set (DS).";
    container ptp-telecom-profile {
      presence
        "When present, the PTP Transparent Clock (TC) Node is a
        PTP Telecom Profile TC Node.

        The conformance level of optional attributes, default
        values and value ranges are defined in the relevant PTP
        Telecom Profile Recommendations, as defined in
        G.7721.1/Annex A.";
      status deprecated;
      description
        "The additional Default data set (DS) members of the PTP
         Telecom Profile Transparent Clock (TC) Node.";
      container profile-identifier {
        status deprecated;
        description
          "The PTP Telecom Profile which applies to the PTP
          Transparent Clock (TC) Node.";
        reference
          "ITU-T G.8275.1 v4.2 (Draft): annex A.1";
        uses ptp-tlp-profile-identifier {
          status deprecated;
        }
      }
      reference
        "ITU-T G.8275.1 v4.2 (Draft): table A.6
         
         ITU-T G.7721.1 v1.1 (Draft): Annex A";
    }
  }
}
