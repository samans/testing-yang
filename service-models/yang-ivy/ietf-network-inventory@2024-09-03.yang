module ietf-network-inventory {
  yang-version 1.1;
  namespace "urn:ietf:params:xml:ns:yang:ietf-network-inventory";
  prefix ni;

  import iana-hardware {
    prefix ianahw;
    reference
      "https://www.iana.org/assignments/yang-parameters";
  }
  import ietf-yang-types {
    prefix yang;
    reference
      "RFC6991: Common YANG Data Types.";
  }
  import ietf-inet-types {
    prefix inet;
    reference
      "RFC6991: Common YANG Data Types.";
  }

  organization
    "IETF IVY Working Group";
  contact
    "WG Web:   <https://datatracker.ietf.org/wg/ivy/>
     WG List:  <mailto:inventory-yang@ietf.org>

     Editor:   Chaode Yu
               <yuchaode@huawei.com>

     Editor:   Sergio Belotti
               <sergio.belotti@nokia.com>

     Editor:   Jean-Francois Bouquier
               <jeff.bouquier@vodafone.com>

     Editor:   Fabio Peruzzini
               <fabio.peruzzini@telecomitalia.it>

     Editor:   Phil Bedard
               <phbedard@cisco.com>";
  description
    "This module defines a base model for retrieving network
     inventory.

     The model fully conforms to the Network Management
     Datastore Architecture (NMDA).

     Copyright (c) 2023 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  // RFC Ed.: replace XXXX with actual RFC number and remove this
  // note.
  // RFC Ed.: update the date below with the date of RFC publication
  // and remove this note.

  revision 2024-09-03 {
    description
      "Initial version hacked";
    reference
      "RFC XXXX: A YANG Data Model for Network Inventory.";
    //RFC Editor: replace XXXX with actual RFC number, update date
    //information and remove this note
  }

  identity non-hardware-component-class {
    description
      "Base identity for non hardware components (e.g., software
       components) in a managed device.";
  }

  identity ne-type {
    description
      "Base identity for network element (NE) types.";
  }

  identity ne-physical {
    base ni:ne-type;
    description
      "A physical network element (NE). ";
  }

  grouping common-entity-attributes {
    description
      "A set of attributes which are common to all the entities
       (e.g., component, equipment room) defined in this module.";
    leaf uuid {
      type yang:uuid;
      config false;
      description
        "Uniquely identifies an entity (e.g., component).";
    }
    leaf name {
      type string;
      description
        "A name for an entity (e.g., component), as specified by
         a network manager, that provides a non-volatile 'handle'
         for the entity and that can be modified anytime during the
         entity lifetime.

         If no configured value exists, the server MAY set the value
         of this node to a locally unique value in the operational
         state.";
    }
    leaf description {
      type string;
      description
        "a textual description of inventory object";
    }
    leaf alias {
      type string;
      description
        "a alias name of inventory objects. This alias name can be
         specified by network manager.";
    }
  }

  grouping ne-specific-info-grouping {
    description
      "Attributes applicable to network elements.";
    leaf hardware-rev {
      type string;
      config false;
      description
        "The vendor-specific hardware revision string for the NE.";
    }
    leaf software-rev {
      type string;
      config false;
      description
        "The vendor-specific software revision string for the NE.";
    }
    leaf-list software-patch-rev {
      type string;
      config false;
      description
        "The vendor-specific patch software revision string for the
         NE.";
    }
    leaf mfg-name {
      type string;
      config false;
      description
        "The name of the manufacturer of this NE";
    }
    leaf mfg-date {
      type yang:date-and-time;
      config false;
      description
        "The date of manufacturing of the NE.";
    }
    leaf serial-number {
      type string;
      config false;
      description
        "The vendor-specific serial number of the network element
         instance. It is expected that vendors assign unique serial
         numbers to different network element instances within the
         scope of the product name.";
    }
    leaf product-name {
      type string;
      config false;
      description
        "The vendor-specific and human-interpretable string
         describing the network element type. It is expected that
         vendors assign unique product names to different NE types
         within the scope of the vendor.";
    }
  }

  grouping component-specific-info-grouping {
    description
      "Provide component-specific attributes for different
       components.";
    container chassis-specific-info {
      when "derived-from-or-self(../class, 'ianahw:chassis')";
      config false;
      description
        "This container contains some attributes belong to
         chassis only.";
      uses chassis-specific-info-grouping;
    }
    container slot-specific-info {
      when "derived-from-or-self(../class, 'ianahw:container')";
      config false;
      description
        "This container contains some attributes belong to
         slot only.";
      uses slot-specific-info-grouping;
    }
    container board-specific-info {
      when "derived-from-or-self(../class, 'ianahw:module')";
      config false;
      description
        "This container contains some attributes belong to
         board only.";
      uses board-specific-info-grouping;
    }
    container port-specific-info {
      when "derived-from-or-self(../class, 'ianahw:port')";
      config false;
      description
        "This container contains some attributes belong to
         port only.";
      uses port-specific-info-grouping;
    }
  }

  grouping chassis-specific-info-grouping {
    //To be enriched in the future.
    description
      "Specific attributes applicable to chassis only.";
  }

  grouping slot-specific-info-grouping {
    //To be enriched in the future.
    description
      "Specific attributes applicable to slots only.";
  }

  grouping board-specific-info-grouping {
    //To be enriched in the future.
    description
      "Specific attributes applicable to boards only.";
  }

  grouping port-specific-info-grouping {
    //To be enriched in the future.
    description
      "Specific attributes applicable to ports only.";
  }

  grouping ne-info-grouping {
    description
      "Grouping for network elements.";
    container network-elements {
      description
        "The top-level container for the list of network elements
         within the network.";
      list network-element {
        key "ne-id";
        description
          "The list of network elements within the network.";
        leaf ne-id {
          type string;
          description
            "Network Element (NE) identifier.";
        }
        leaf ne-type {
          type identityref {
            base ne-type;
          }
          default "ne-physical";
          config false;
          description
            "The type of network element (NE).";
        }
        uses common-entity-attributes;
        uses ne-specific-info-grouping;
        container components {
          description
            "The top-level container for the list of components
             within a network element.";
          list component {
            key "component-id";
            description
              "The list of components within a network element.";
            leaf component-id {
              type string;
              description
                "Component identifier";
            }
            leaf class {
              type union {
                type identityref {
                  base ianahw:hardware-class;
                }
                type identityref {
                  base non-hardware-component-class;
                }
              }
              config false;
              mandatory true;
              description
                "The type of the component.";
            }
            uses common-entity-attributes;
            container child-component-ref {
              config false;
              description
                "A placeholder for adding the reference to child
                 component(s): to further discuss whether to define
                 a child leaf-list as RFC8348 or a list of
                 sub-components as openconfig-platform.";
            }
            leaf parent-rel-pos {
              type int32 {
                range "0 .. 2147483647";
              }
              config false;
              description
                "The relative position with respect to the parent
                 component among all the sibling components.";
              reference
                "RFC 6933: Entity MIB (Version 4) -
                          entPhysicalParentRelPos";
            }
            container parent-component-ref {
              config false;
              description
                "A placeholder for adding the reference to parent
                 component(s): to further discuss whether to define
                 a parent attribute as RFC8348 or a
                 parent-component-references container as in
                 draft-ietf-ccamp-network-inventory-yang-02.";
            }
            leaf hardware-rev {
              type string;
              config false;
              description
                "The vendor-specific hardware revision string for the
                 component.  The preferred value is the hardware
                 revision identifier actually printed on the
                 component itself (if present).";
              reference
                "RFC 6933: Entity MIB (Version 4) -
                          entPhysicalHardwareRev";
            }
            leaf firmware-rev {
              type string;
              config false;
              description
                "The vendor-specific firmware revision string for the
                 component.";
              reference
                "RFC 6933: Entity MIB (Version 4) -
                          entPhysicalFirmwareRev";
            }
            leaf software-rev {
              type string;
              config false;
              description
                "The vendor-specific software revision string for the
                 component.";
              reference
                "RFC 6933: Entity MIB (Version 4) -
                          entPhysicalSoftwareRev";
            }
            leaf-list software-patch-rev {
              type string;
              config false;
              description
                "The vendor-specific patch software revision string
                 for the component.";
            }
            leaf serial-num {
              type string;
              config false;
              description
                "The vendor-specific serial number of the component
                 instance. It is expected that vendors assign unique
                 serial numbers to different component instances
                 within the scope of the part number.";
            }
            leaf mfg-name {
              type string;
              config false;
              description
                "The name of the manufacturer of this physical
                 component.
                 The preferred value is the manufacturer name string
                 actually printed on the component itself
                 (if present).

                 Note that comparisons between instances of the
                 'model-name', 'firmware-rev', 'software-rev', and
                 'serial-num' nodes are only meaningful amongst
                 components with the same value of 'mfg-name'.

                 If the manufacturer name string associated with the
                 physical component is unknown to the server, then
                 this node is not instantiated.";
              reference
                "RFC 6933: Entity MIB (Version 4) -
                 entPhysicalMfgName";
            }
            leaf part-number {
              type string;
              config false;
              description
                "The vendor-specific part number of the component
                 type. It is expected that vendors assign unique part
                 numbers to different component types within the
                 scope of the vendor.";
            }
            leaf product-name {
              type string;
              config false;
              description
                "The vendor-specific and human-interpretable string
                 describing the component type. It is expected that
                 vendors assign unique product names to different
                 component types within the scope of the vendor.";
            }
            leaf asset-id {
              type string;
              config false;
              description
                "This node is a user-assigned asset tracking
                 identifier for the component.

                 A server implementation MAY map this leaf to the
                 entPhysicalAssetID MIB object.  Such an
                 implementation needs to use some mechanism to handle
                 the differences in size and characters allowed
                 between this leaf and entPhysicalAssetID.

                 The definition of such a mechanism is outside the
                 scope of this document.";
              reference
                "RFC 6933: Entity MIB (Version 4) -
                 entPhysicalAssetID";
            }
            leaf is-fru {
              type boolean;
              config false;
              description
                "This node indicates whether or not this component is
                 considered a 'field-replaceable unit' by the vendor.
                 If this node contains the value 'true', then this
                 component identifies a field-replaceable unit.
                 For all components that are permanently contained
                 within a field-replaceable unit, the value 'false'
                 should be returned for this node.";
              reference
                "RFC 6933: Entity MIB (Version 4) -
                 entPhysicalIsFRU";
            }
            leaf mfg-date {
              type yang:date-and-time;
              config false;
              description
                "The date of manufacturing of the managed
                component.";
              reference
                "RFC 6933: Entity MIB (Version 4) -
                 entPhysicalMfgDate";
            }
            leaf-list uri {
              type inet:uri;
              config false;
              description
                "This node contains identification information about
                 the component.";
              reference
                "RFC 6933: Entity MIB (Version 4) - entPhysicalUris";
            }
            uses component-specific-info-grouping;
          }
        }
      }
    }
  }

  container network-inventory {
    description
      "Top-level container for network inventory.";
    uses ne-info-grouping;
  }
}
