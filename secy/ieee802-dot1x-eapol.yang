module ieee802-dot1x-eapol {
  yang-version "1.1";
  namespace urn:ieee:std:802.1X:yang:ieee802-dot1x-eapol;
  prefix eapol;
  import ietf-interfaces {
    prefix if;
  }
  import ieee802-dot1x{
    prefix dot1x;
  }
  import ieee802-types {
    prefix ieee;
  }

  organization
    "Institute of Electrical and Electronics Engineers";
  contact
    "WG-URL: http://ieee802.org/1/
    WG-EMail: stds-802-1-l@ieee.org
    
    Contact: IEEE 802.1 Working Group Chair
    Postal: C/O IEEE 802.1 Working Group
           IEEE Standards Association
           445 Hoes Lane
           Piscataway, NJ 08855
           USA
    
    E-mail: stds-802-1-chairs@ieee.org";
  description
    "Missing Eapol Address for 802.1X-2020";
  revision 2022-02-08 {
    description
      "Augment to be added to 802.1X on next revision";
    reference
      "IEEE Std 802.1X-2020, Port-Based Network Access Control.";
  }
  
  augment "/if:interfaces/if:interface/dot1x:pae" {
    leaf eapol-group-address {
      type ieee:mac-address;
      description
        "The destination Group MAC Address used by this PAE
         when transmitting EAPOL frames.";
      reference
        "IEEE 802.1X-2020 Clause 12.9, Figure 12-3";
    }
  }
}
